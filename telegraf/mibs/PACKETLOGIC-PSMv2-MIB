PACKETLOGIC-PSMv2-MIB DEFINITIONS ::= BEGIN

IMPORTS
	MODULE-IDENTITY, OBJECT-TYPE, Counter64,
	enterprises FROM SNMPv2-SMI
	CounterBasedGauge64 FROM HCNUM-TC
	DateAndTime, DisplayString FROM SNMPv2-TC;

psmSysdiag MODULE-IDENTITY
	LAST-UPDATED "201612071400Z"
	ORGANIZATION "Procera Networks, Inc."
	CONTACT-INFO
		"Procera Networks support
		 Email: support@proceranetworks.com"
	DESCRIPTION
		"The MIB module for PacketLogic Subscriber Manager"
	REVISION     "201612071400Z"
	DESCRIPTION
		"Latest version at the revision date"
	::= { plm 3 }

procera OBJECT IDENTIFIER ::= { enterprises 15397 }
plm OBJECT IDENTIFIER ::= { procera 3 }
psmv2 OBJECT IDENTIFIER ::= { psmSysdiag 2 }

psmDiameter OBJECT IDENTIFIER ::= { psmv2 17 }

psmDiameterBrokenAnswersReceived OBJECT IDENTIFIER ::= { psmDiameter 1 }

psmDiameterBrokenAnswersReceivedVal OBJECT-TYPE
	SYNTAX     Counter64
	MAX-ACCESS read-only
	STATUS     current
	DESCRIPTION "Broken answers received"

	::={ psmDiameterBrokenAnswersReceived 1 }

psmDiameterBrokenAnswersReceivedMom OBJECT-TYPE
	SYNTAX     CounterBasedGauge64
	MAX-ACCESS read-only
	STATUS     current
	DESCRIPTION "Broken answers received"

	::={ psmDiameterBrokenAnswersReceived 2 }

psmDiameterBrokenAnswersReceivedMax OBJECT-TYPE
	SYNTAX     CounterBasedGauge64
	MAX-ACCESS read-only
	STATUS     current
	DESCRIPTION "Broken answers received"

	::={ psmDiameterBrokenAnswersReceived 3 }

psmDiameterBrokenAnswersReceivedLevelTable OBJECT-TYPE
	SYNTAX     SEQUENCE OF PsmDiameterBrokenAnswersReceivedLevelEntry
	MAX-ACCESS not-accessible
	STATUS     current
	DESCRIPTION
	"Broken answers received"
	::={ psmDiameterBrokenAnswersReceived 4 }

psmDiameterBrokenAnswersReceivedLevelEntry OBJECT-TYPE
	SYNTAX      PsmDiameterBrokenAnswersReceivedLevelEntry
	MAX-ACCESS  not-accessible
	STATUS      current
	DESCRIPTION
	"Broken answers received"
	INDEX { psmDiameterBrokenAnswersReceivedLevelName }
	::={ psmDiameterBrokenAnswersReceivedLevelTable 1 }

PsmDiameterBrokenAnswersReceivedLevelEntry ::=
	SEQUENCE {
		psmDiameterBrokenAnswersReceivedLevelName DisplayString,
		psmDiameterBrokenAnswersReceivedLevelVal  Counter64,
		psmDiameterBrokenAnswersReceivedLevelMom  CounterBasedGauge64,
		psmDiameterBrokenAnswersReceivedLevelMax  CounterBasedGauge64
	}

psmDiameterBrokenAnswersReceivedLevelName OBJECT-TYPE
	SYNTAX      DisplayString
	MAX-ACCESS  not-accessible
	STATUS      current
	DESCRIPTION
	"Broken answers received"
	::={ psmDiameterBrokenAnswersReceivedLevelEntry 1}

psmDiameterBrokenAnswersReceivedLevelVal OBJECT-TYPE
	SYNTAX     Counter64
	MAX-ACCESS read-only
	STATUS     current
	DESCRIPTION
	"Broken answers received"
	::={ psmDiameterBrokenAnswersReceivedLevelEntry 2 }

psmDiameterBrokenAnswersReceivedLevelMom OBJECT-TYPE
	SYNTAX     CounterBasedGauge64
	MAX-ACCESS read-only
	STATUS     current
	DESCRIPTION
	"Broken answers received"
	::={ psmDiameterBrokenAnswersReceivedLevelEntry 3 }

psmDiameterBrokenAnswersReceivedLevelMax OBJECT-TYPE
	SYNTAX     CounterBasedGauge64
	MAX-ACCESS read-only
	STATUS     current
	DESCRIPTION
	"Broken answers received"
	::={ psmDiameterBrokenAnswersReceivedLevelEntry 4 }

psmDiameterBrokenRequestsReceived OBJECT IDENTIFIER ::= { psmDiameter 2 }

psmDiameterBrokenRequestsReceivedVal OBJECT-TYPE
	SYNTAX     Counter64
	MAX-ACCESS read-only
	STATUS     current
	DESCRIPTION "Broken requests received"

	::={ psmDiameterBrokenRequestsReceived 1 }

psmDiameterBrokenRequestsReceivedMom OBJECT-TYPE
	SYNTAX     CounterBasedGauge64
	MAX-ACCESS read-only
	STATUS     current
	DESCRIPTION "Broken requests received"

	::={ psmDiameterBrokenRequestsReceived 2 }

psmDiameterBrokenRequestsReceivedMax OBJECT-TYPE
	SYNTAX     CounterBasedGauge64
	MAX-ACCESS read-only
	STATUS     current
	DESCRIPTION "Broken requests received"

	::={ psmDiameterBrokenRequestsReceived 3 }

psmDiameterBrokenRequestsReceivedLevelTable OBJECT-TYPE
	SYNTAX     SEQUENCE OF PsmDiameterBrokenRequestsReceivedLevelEntry
	MAX-ACCESS not-accessible
	STATUS     current
	DESCRIPTION
	"Broken requests received"
	::={ psmDiameterBrokenRequestsReceived 4 }

psmDiameterBrokenRequestsReceivedLevelEntry OBJECT-TYPE
	SYNTAX      PsmDiameterBrokenRequestsReceivedLevelEntry
	MAX-ACCESS  not-accessible
	STATUS      current
	DESCRIPTION
	"Broken requests received"
	INDEX { psmDiameterBrokenRequestsReceivedLevelName }
	::={ psmDiameterBrokenRequestsReceivedLevelTable 1 }

PsmDiameterBrokenRequestsReceivedLevelEntry ::=
	SEQUENCE {
		psmDiameterBrokenRequestsReceivedLevelName DisplayString,
		psmDiameterBrokenRequestsReceivedLevelVal  Counter64,
		psmDiameterBrokenRequestsReceivedLevelMom  CounterBasedGauge64,
		psmDiameterBrokenRequestsReceivedLevelMax  CounterBasedGauge64
	}

psmDiameterBrokenRequestsReceivedLevelName OBJECT-TYPE
	SYNTAX      DisplayString
	MAX-ACCESS  not-accessible
	STATUS      current
	DESCRIPTION
	"Broken requests received"
	::={ psmDiameterBrokenRequestsReceivedLevelEntry 1}

psmDiameterBrokenRequestsReceivedLevelVal OBJECT-TYPE
	SYNTAX     Counter64
	MAX-ACCESS read-only
	STATUS     current
	DESCRIPTION
	"Broken requests received"
	::={ psmDiameterBrokenRequestsReceivedLevelEntry 2 }

psmDiameterBrokenRequestsReceivedLevelMom OBJECT-TYPE
	SYNTAX     CounterBasedGauge64
	MAX-ACCESS read-only
	STATUS     current
	DESCRIPTION
	"Broken requests received"
	::={ psmDiameterBrokenRequestsReceivedLevelEntry 3 }

psmDiameterBrokenRequestsReceivedLevelMax OBJECT-TYPE
	SYNTAX     CounterBasedGauge64
	MAX-ACCESS read-only
	STATUS     current
	DESCRIPTION
	"Broken requests received"
	::={ psmDiameterBrokenRequestsReceivedLevelEntry 4 }

psmDiameterReceivedBytes OBJECT IDENTIFIER ::= { psmDiameter 3 }

psmDiameterReceivedBytesVal OBJECT-TYPE
	SYNTAX     Counter64
	MAX-ACCESS read-only
	STATUS     current
	DESCRIPTION "Received bytes"

	::={ psmDiameterReceivedBytes 1 }

psmDiameterReceivedBytesMom OBJECT-TYPE
	SYNTAX     CounterBasedGauge64
	MAX-ACCESS read-only
	STATUS     current
	DESCRIPTION "Received bytes"

	::={ psmDiameterReceivedBytes 2 }

psmDiameterReceivedBytesMax OBJECT-TYPE
	SYNTAX     CounterBasedGauge64
	MAX-ACCESS read-only
	STATUS     current
	DESCRIPTION "Received bytes"

	::={ psmDiameterReceivedBytes 3 }

psmDiameterReceivedBytesLevelTable OBJECT-TYPE
	SYNTAX     SEQUENCE OF PsmDiameterReceivedBytesLevelEntry
	MAX-ACCESS not-accessible
	STATUS     current
	DESCRIPTION
	"Received bytes"
	::={ psmDiameterReceivedBytes 4 }

psmDiameterReceivedBytesLevelEntry OBJECT-TYPE
	SYNTAX      PsmDiameterReceivedBytesLevelEntry
	MAX-ACCESS  not-accessible
	STATUS      current
	DESCRIPTION
	"Received bytes"
	INDEX { psmDiameterReceivedBytesLevelName }
	::={ psmDiameterReceivedBytesLevelTable 1 }

PsmDiameterReceivedBytesLevelEntry ::=
	SEQUENCE {
		psmDiameterReceivedBytesLevelName DisplayString,
		psmDiameterReceivedBytesLevelVal  Counter64,
		psmDiameterReceivedBytesLevelMom  CounterBasedGauge64,
		psmDiameterReceivedBytesLevelMax  CounterBasedGauge64
	}

psmDiameterReceivedBytesLevelName OBJECT-TYPE
	SYNTAX      DisplayString
	MAX-ACCESS  not-accessible
	STATUS      current
	DESCRIPTION
	"Received bytes"
	::={ psmDiameterReceivedBytesLevelEntry 1}

psmDiameterReceivedBytesLevelVal OBJECT-TYPE
	SYNTAX     Counter64
	MAX-ACCESS read-only
	STATUS     current
	DESCRIPTION
	"Received bytes"
	::={ psmDiameterReceivedBytesLevelEntry 2 }

psmDiameterReceivedBytesLevelMom OBJECT-TYPE
	SYNTAX     CounterBasedGauge64
	MAX-ACCESS read-only
	STATUS     current
	DESCRIPTION
	"Received bytes"
	::={ psmDiameterReceivedBytesLevelEntry 3 }

psmDiameterReceivedBytesLevelMax OBJECT-TYPE
	SYNTAX     CounterBasedGauge64
	MAX-ACCESS read-only
	STATUS     current
	DESCRIPTION
	"Received bytes"
	::={ psmDiameterReceivedBytesLevelEntry 4 }

psmDiameterSentBytes OBJECT IDENTIFIER ::= { psmDiameter 4 }

psmDiameterSentBytesVal OBJECT-TYPE
	SYNTAX     Counter64
	MAX-ACCESS read-only
	STATUS     current
	DESCRIPTION "Sent bytes"

	::={ psmDiameterSentBytes 1 }

psmDiameterSentBytesMom OBJECT-TYPE
	SYNTAX     CounterBasedGauge64
	MAX-ACCESS read-only
	STATUS     current
	DESCRIPTION "Sent bytes"

	::={ psmDiameterSentBytes 2 }

psmDiameterSentBytesMax OBJECT-TYPE
	SYNTAX     CounterBasedGauge64
	MAX-ACCESS read-only
	STATUS     current
	DESCRIPTION "Sent bytes"

	::={ psmDiameterSentBytes 3 }

psmDiameterSentBytesLevelTable OBJECT-TYPE
	SYNTAX     SEQUENCE OF PsmDiameterSentBytesLevelEntry
	MAX-ACCESS not-accessible
	STATUS     current
	DESCRIPTION
	"Sent bytes"
	::={ psmDiameterSentBytes 4 }

psmDiameterSentBytesLevelEntry OBJECT-TYPE
	SYNTAX      PsmDiameterSentBytesLevelEntry
	MAX-ACCESS  not-accessible
	STATUS      current
	DESCRIPTION
	"Sent bytes"
	INDEX { psmDiameterSentBytesLevelName }
	::={ psmDiameterSentBytesLevelTable 1 }

PsmDiameterSentBytesLevelEntry ::=
	SEQUENCE {
		psmDiameterSentBytesLevelName DisplayString,
		psmDiameterSentBytesLevelVal  Counter64,
		psmDiameterSentBytesLevelMom  CounterBasedGauge64,
		psmDiameterSentBytesLevelMax  CounterBasedGauge64
	}

psmDiameterSentBytesLevelName OBJECT-TYPE
	SYNTAX      DisplayString
	MAX-ACCESS  not-accessible
	STATUS      current
	DESCRIPTION
	"Sent bytes"
	::={ psmDiameterSentBytesLevelEntry 1}

psmDiameterSentBytesLevelVal OBJECT-TYPE
	SYNTAX     Counter64
	MAX-ACCESS read-only
	STATUS     current
	DESCRIPTION
	"Sent bytes"
	::={ psmDiameterSentBytesLevelEntry 2 }

psmDiameterSentBytesLevelMom OBJECT-TYPE
	SYNTAX     CounterBasedGauge64
	MAX-ACCESS read-only
	STATUS     current
	DESCRIPTION
	"Sent bytes"
	::={ psmDiameterSentBytesLevelEntry 3 }

psmDiameterSentBytesLevelMax OBJECT-TYPE
	SYNTAX     CounterBasedGauge64
	MAX-ACCESS read-only
	STATUS     current
	DESCRIPTION
	"Sent bytes"
	::={ psmDiameterSentBytesLevelEntry 4 }

psmDiameterDeviceWatchdogAnswersReceived OBJECT IDENTIFIER ::= { psmDiameter 5 }

psmDiameterDeviceWatchdogAnswersReceivedVal OBJECT-TYPE
	SYNTAX     Counter64
	MAX-ACCESS read-only
	STATUS     current
	DESCRIPTION "Device-Watchdog answers received"

	::={ psmDiameterDeviceWatchdogAnswersReceived 1 }

psmDiameterDeviceWatchdogAnswersReceivedMom OBJECT-TYPE
	SYNTAX     CounterBasedGauge64
	MAX-ACCESS read-only
	STATUS     current
	DESCRIPTION "Device-Watchdog answers received"

	::={ psmDiameterDeviceWatchdogAnswersReceived 2 }

psmDiameterDeviceWatchdogAnswersReceivedMax OBJECT-TYPE
	SYNTAX     CounterBasedGauge64
	MAX-ACCESS read-only
	STATUS     current
	DESCRIPTION "Device-Watchdog answers received"

	::={ psmDiameterDeviceWatchdogAnswersReceived 3 }

psmDiameterDeviceWatchdogAnswersReceivedLevelTable OBJECT-TYPE
	SYNTAX     SEQUENCE OF PsmDiameterDeviceWatchdogAnswersReceivedLevelEntry
	MAX-ACCESS not-accessible
	STATUS     current
	DESCRIPTION
	"Device-Watchdog answers received"
	::={ psmDiameterDeviceWatchdogAnswersReceived 4 }

psmDiameterDeviceWatchdogAnswersReceivedLevelEntry OBJECT-TYPE
	SYNTAX      PsmDiameterDeviceWatchdogAnswersReceivedLevelEntry
	MAX-ACCESS  not-accessible
	STATUS      current
	DESCRIPTION
	"Device-Watchdog answers received"
	INDEX { psmDiameterDeviceWatchdogAnswersReceivedLevelName }
	::={ psmDiameterDeviceWatchdogAnswersReceivedLevelTable 1 }

PsmDiameterDeviceWatchdogAnswersReceivedLevelEntry ::=
	SEQUENCE {
		psmDiameterDeviceWatchdogAnswersReceivedLevelName DisplayString,
		psmDiameterDeviceWatchdogAnswersReceivedLevelVal  Counter64,
		psmDiameterDeviceWatchdogAnswersReceivedLevelMom  CounterBasedGauge64,
		psmDiameterDeviceWatchdogAnswersReceivedLevelMax  CounterBasedGauge64
	}

psmDiameterDeviceWatchdogAnswersReceivedLevelName OBJECT-TYPE
	SYNTAX      DisplayString
	MAX-ACCESS  not-accessible
	STATUS      current
	DESCRIPTION
	"Device-Watchdog answers received"
	::={ psmDiameterDeviceWatchdogAnswersReceivedLevelEntry 1}

psmDiameterDeviceWatchdogAnswersReceivedLevelVal OBJECT-TYPE
	SYNTAX     Counter64
	MAX-ACCESS read-only
	STATUS     current
	DESCRIPTION
	"Device-Watchdog answers received"
	::={ psmDiameterDeviceWatchdogAnswersReceivedLevelEntry 2 }

psmDiameterDeviceWatchdogAnswersReceivedLevelMom OBJECT-TYPE
	SYNTAX     CounterBasedGauge64
	MAX-ACCESS read-only
	STATUS     current
	DESCRIPTION
	"Device-Watchdog answers received"
	::={ psmDiameterDeviceWatchdogAnswersReceivedLevelEntry 3 }

psmDiameterDeviceWatchdogAnswersReceivedLevelMax OBJECT-TYPE
	SYNTAX     CounterBasedGauge64
	MAX-ACCESS read-only
	STATUS     current
	DESCRIPTION
	"Device-Watchdog answers received"
	::={ psmDiameterDeviceWatchdogAnswersReceivedLevelEntry 4 }

psmDiameterDeviceWatchdogAnswersSent OBJECT IDENTIFIER ::= { psmDiameter 6 }

psmDiameterDeviceWatchdogAnswersSentVal OBJECT-TYPE
	SYNTAX     Counter64
	MAX-ACCESS read-only
	STATUS     current
	DESCRIPTION "Device-Watchdog answers sent"

	::={ psmDiameterDeviceWatchdogAnswersSent 1 }

psmDiameterDeviceWatchdogAnswersSentMom OBJECT-TYPE
	SYNTAX     CounterBasedGauge64
	MAX-ACCESS read-only
	STATUS     current
	DESCRIPTION "Device-Watchdog answers sent"

	::={ psmDiameterDeviceWatchdogAnswersSent 2 }

psmDiameterDeviceWatchdogAnswersSentMax OBJECT-TYPE
	SYNTAX     CounterBasedGauge64
	MAX-ACCESS read-only
	STATUS     current
	DESCRIPTION "Device-Watchdog answers sent"

	::={ psmDiameterDeviceWatchdogAnswersSent 3 }

psmDiameterDeviceWatchdogAnswersSentLevelTable OBJECT-TYPE
	SYNTAX     SEQUENCE OF PsmDiameterDeviceWatchdogAnswersSentLevelEntry
	MAX-ACCESS not-accessible
	STATUS     current
	DESCRIPTION
	"Device-Watchdog answers sent"
	::={ psmDiameterDeviceWatchdogAnswersSent 4 }

psmDiameterDeviceWatchdogAnswersSentLevelEntry OBJECT-TYPE
	SYNTAX      PsmDiameterDeviceWatchdogAnswersSentLevelEntry
	MAX-ACCESS  not-accessible
	STATUS      current
	DESCRIPTION
	"Device-Watchdog answers sent"
	INDEX { psmDiameterDeviceWatchdogAnswersSentLevelName }
	::={ psmDiameterDeviceWatchdogAnswersSentLevelTable 1 }

PsmDiameterDeviceWatchdogAnswersSentLevelEntry ::=
	SEQUENCE {
		psmDiameterDeviceWatchdogAnswersSentLevelName DisplayString,
		psmDiameterDeviceWatchdogAnswersSentLevelVal  Counter64,
		psmDiameterDeviceWatchdogAnswersSentLevelMom  CounterBasedGauge64,
		psmDiameterDeviceWatchdogAnswersSentLevelMax  CounterBasedGauge64
	}

psmDiameterDeviceWatchdogAnswersSentLevelName OBJECT-TYPE
	SYNTAX      DisplayString
	MAX-ACCESS  not-accessible
	STATUS      current
	DESCRIPTION
	"Device-Watchdog answers sent"
	::={ psmDiameterDeviceWatchdogAnswersSentLevelEntry 1}

psmDiameterDeviceWatchdogAnswersSentLevelVal OBJECT-TYPE
	SYNTAX     Counter64
	MAX-ACCESS read-only
	STATUS     current
	DESCRIPTION
	"Device-Watchdog answers sent"
	::={ psmDiameterDeviceWatchdogAnswersSentLevelEntry 2 }

psmDiameterDeviceWatchdogAnswersSentLevelMom OBJECT-TYPE
	SYNTAX     CounterBasedGauge64
	MAX-ACCESS read-only
	STATUS     current
	DESCRIPTION
	"Device-Watchdog answers sent"
	::={ psmDiameterDeviceWatchdogAnswersSentLevelEntry 3 }

psmDiameterDeviceWatchdogAnswersSentLevelMax OBJECT-TYPE
	SYNTAX     CounterBasedGauge64
	MAX-ACCESS read-only
	STATUS     current
	DESCRIPTION
	"Device-Watchdog answers sent"
	::={ psmDiameterDeviceWatchdogAnswersSentLevelEntry 4 }

psmDiameterDeviceWatchdogRequestsReceived OBJECT IDENTIFIER ::= { psmDiameter 7 }

psmDiameterDeviceWatchdogRequestsReceivedVal OBJECT-TYPE
	SYNTAX     Counter64
	MAX-ACCESS read-only
	STATUS     current
	DESCRIPTION "Device-Watchdog requests received"

	::={ psmDiameterDeviceWatchdogRequestsReceived 1 }

psmDiameterDeviceWatchdogRequestsReceivedMom OBJECT-TYPE
	SYNTAX     CounterBasedGauge64
	MAX-ACCESS read-only
	STATUS     current
	DESCRIPTION "Device-Watchdog requests received"

	::={ psmDiameterDeviceWatchdogRequestsReceived 2 }

psmDiameterDeviceWatchdogRequestsReceivedMax OBJECT-TYPE
	SYNTAX     CounterBasedGauge64
	MAX-ACCESS read-only
	STATUS     current
	DESCRIPTION "Device-Watchdog requests received"

	::={ psmDiameterDeviceWatchdogRequestsReceived 3 }

psmDiameterDeviceWatchdogRequestsReceivedLevelTable OBJECT-TYPE
	SYNTAX     SEQUENCE OF PsmDiameterDeviceWatchdogRequestsReceivedLevelEntry
	MAX-ACCESS not-accessible
	STATUS     current
	DESCRIPTION
	"Device-Watchdog requests received"
	::={ psmDiameterDeviceWatchdogRequestsReceived 4 }

psmDiameterDeviceWatchdogRequestsReceivedLevelEntry OBJECT-TYPE
	SYNTAX      PsmDiameterDeviceWatchdogRequestsReceivedLevelEntry
	MAX-ACCESS  not-accessible
	STATUS      current
	DESCRIPTION
	"Device-Watchdog requests received"
	INDEX { psmDiameterDeviceWatchdogRequestsReceivedLevelName }
	::={ psmDiameterDeviceWatchdogRequestsReceivedLevelTable 1 }

PsmDiameterDeviceWatchdogRequestsReceivedLevelEntry ::=
	SEQUENCE {
		psmDiameterDeviceWatchdogRequestsReceivedLevelName DisplayString,
		psmDiameterDeviceWatchdogRequestsReceivedLevelVal  Counter64,
		psmDiameterDeviceWatchdogRequestsReceivedLevelMom  CounterBasedGauge64,
		psmDiameterDeviceWatchdogRequestsReceivedLevelMax  CounterBasedGauge64
	}

psmDiameterDeviceWatchdogRequestsReceivedLevelName OBJECT-TYPE
	SYNTAX      DisplayString
	MAX-ACCESS  not-accessible
	STATUS      current
	DESCRIPTION
	"Device-Watchdog requests received"
	::={ psmDiameterDeviceWatchdogRequestsReceivedLevelEntry 1}

psmDiameterDeviceWatchdogRequestsReceivedLevelVal OBJECT-TYPE
	SYNTAX     Counter64
	MAX-ACCESS read-only
	STATUS     current
	DESCRIPTION
	"Device-Watchdog requests received"
	::={ psmDiameterDeviceWatchdogRequestsReceivedLevelEntry 2 }

psmDiameterDeviceWatchdogRequestsReceivedLevelMom OBJECT-TYPE
	SYNTAX     CounterBasedGauge64
	MAX-ACCESS read-only
	STATUS     current
	DESCRIPTION
	"Device-Watchdog requests received"
	::={ psmDiameterDeviceWatchdogRequestsReceivedLevelEntry 3 }

psmDiameterDeviceWatchdogRequestsReceivedLevelMax OBJECT-TYPE
	SYNTAX     CounterBasedGauge64
	MAX-ACCESS read-only
	STATUS     current
	DESCRIPTION
	"Device-Watchdog requests received"
	::={ psmDiameterDeviceWatchdogRequestsReceivedLevelEntry 4 }

psmDiameterDeviceWatchdogRequestsSent OBJECT IDENTIFIER ::= { psmDiameter 8 }

psmDiameterDeviceWatchdogRequestsSentVal OBJECT-TYPE
	SYNTAX     Counter64
	MAX-ACCESS read-only
	STATUS     current
	DESCRIPTION "Device-Watchdog requests sent"

	::={ psmDiameterDeviceWatchdogRequestsSent 1 }

psmDiameterDeviceWatchdogRequestsSentMom OBJECT-TYPE
	SYNTAX     CounterBasedGauge64
	MAX-ACCESS read-only
	STATUS     current
	DESCRIPTION "Device-Watchdog requests sent"

	::={ psmDiameterDeviceWatchdogRequestsSent 2 }

psmDiameterDeviceWatchdogRequestsSentMax OBJECT-TYPE
	SYNTAX     CounterBasedGauge64
	MAX-ACCESS read-only
	STATUS     current
	DESCRIPTION "Device-Watchdog requests sent"

	::={ psmDiameterDeviceWatchdogRequestsSent 3 }

psmDiameterDeviceWatchdogRequestsSentLevelTable OBJECT-TYPE
	SYNTAX     SEQUENCE OF PsmDiameterDeviceWatchdogRequestsSentLevelEntry
	MAX-ACCESS not-accessible
	STATUS     current
	DESCRIPTION
	"Device-Watchdog requests sent"
	::={ psmDiameterDeviceWatchdogRequestsSent 4 }

psmDiameterDeviceWatchdogRequestsSentLevelEntry OBJECT-TYPE
	SYNTAX      PsmDiameterDeviceWatchdogRequestsSentLevelEntry
	MAX-ACCESS  not-accessible
	STATUS      current
	DESCRIPTION
	"Device-Watchdog requests sent"
	INDEX { psmDiameterDeviceWatchdogRequestsSentLevelName }
	::={ psmDiameterDeviceWatchdogRequestsSentLevelTable 1 }

PsmDiameterDeviceWatchdogRequestsSentLevelEntry ::=
	SEQUENCE {
		psmDiameterDeviceWatchdogRequestsSentLevelName DisplayString,
		psmDiameterDeviceWatchdogRequestsSentLevelVal  Counter64,
		psmDiameterDeviceWatchdogRequestsSentLevelMom  CounterBasedGauge64,
		psmDiameterDeviceWatchdogRequestsSentLevelMax  CounterBasedGauge64
	}

psmDiameterDeviceWatchdogRequestsSentLevelName OBJECT-TYPE
	SYNTAX      DisplayString
	MAX-ACCESS  not-accessible
	STATUS      current
	DESCRIPTION
	"Device-Watchdog requests sent"
	::={ psmDiameterDeviceWatchdogRequestsSentLevelEntry 1}

psmDiameterDeviceWatchdogRequestsSentLevelVal OBJECT-TYPE
	SYNTAX     Counter64
	MAX-ACCESS read-only
	STATUS     current
	DESCRIPTION
	"Device-Watchdog requests sent"
	::={ psmDiameterDeviceWatchdogRequestsSentLevelEntry 2 }

psmDiameterDeviceWatchdogRequestsSentLevelMom OBJECT-TYPE
	SYNTAX     CounterBasedGauge64
	MAX-ACCESS read-only
	STATUS     current
	DESCRIPTION
	"Device-Watchdog requests sent"
	::={ psmDiameterDeviceWatchdogRequestsSentLevelEntry 3 }

psmDiameterDeviceWatchdogRequestsSentLevelMax OBJECT-TYPE
	SYNTAX     CounterBasedGauge64
	MAX-ACCESS read-only
	STATUS     current
	DESCRIPTION
	"Device-Watchdog requests sent"
	::={ psmDiameterDeviceWatchdogRequestsSentLevelEntry 4 }

psmDiameterGyAbortsessionAnswersSent OBJECT IDENTIFIER ::= { psmDiameter 9 }

psmDiameterGyAbortsessionAnswersSentVal OBJECT-TYPE
	SYNTAX     Counter64
	MAX-ACCESS read-only
	STATUS     current
	DESCRIPTION "Gy abort-session answers sent"

	::={ psmDiameterGyAbortsessionAnswersSent 1 }

psmDiameterGyAbortsessionAnswersSentMom OBJECT-TYPE
	SYNTAX     CounterBasedGauge64
	MAX-ACCESS read-only
	STATUS     current
	DESCRIPTION "Gy abort-session answers sent"

	::={ psmDiameterGyAbortsessionAnswersSent 2 }

psmDiameterGyAbortsessionAnswersSentMax OBJECT-TYPE
	SYNTAX     CounterBasedGauge64
	MAX-ACCESS read-only
	STATUS     current
	DESCRIPTION "Gy abort-session answers sent"

	::={ psmDiameterGyAbortsessionAnswersSent 3 }

psmDiameterGyAbortsessionAnswersSentLevelTable OBJECT-TYPE
	SYNTAX     SEQUENCE OF PsmDiameterGyAbortsessionAnswersSentLevelEntry
	MAX-ACCESS not-accessible
	STATUS     current
	DESCRIPTION
	"Gy abort-session answers sent"
	::={ psmDiameterGyAbortsessionAnswersSent 4 }

psmDiameterGyAbortsessionAnswersSentLevelEntry OBJECT-TYPE
	SYNTAX      PsmDiameterGyAbortsessionAnswersSentLevelEntry
	MAX-ACCESS  not-accessible
	STATUS      current
	DESCRIPTION
	"Gy abort-session answers sent"
	INDEX { psmDiameterGyAbortsessionAnswersSentLevelName }
	::={ psmDiameterGyAbortsessionAnswersSentLevelTable 1 }

PsmDiameterGyAbortsessionAnswersSentLevelEntry ::=
	SEQUENCE {
		psmDiameterGyAbortsessionAnswersSentLevelName DisplayString,
		psmDiameterGyAbortsessionAnswersSentLevelVal  Counter64,
		psmDiameterGyAbortsessionAnswersSentLevelMom  CounterBasedGauge64,
		psmDiameterGyAbortsessionAnswersSentLevelMax  CounterBasedGauge64
	}

psmDiameterGyAbortsessionAnswersSentLevelName OBJECT-TYPE
	SYNTAX      DisplayString
	MAX-ACCESS  not-accessible
	STATUS      current
	DESCRIPTION
	"Gy abort-session answers sent"
	::={ psmDiameterGyAbortsessionAnswersSentLevelEntry 1}

psmDiameterGyAbortsessionAnswersSentLevelVal OBJECT-TYPE
	SYNTAX     Counter64
	MAX-ACCESS read-only
	STATUS     current
	DESCRIPTION
	"Gy abort-session answers sent"
	::={ psmDiameterGyAbortsessionAnswersSentLevelEntry 2 }

psmDiameterGyAbortsessionAnswersSentLevelMom OBJECT-TYPE
	SYNTAX     CounterBasedGauge64
	MAX-ACCESS read-only
	STATUS     current
	DESCRIPTION
	"Gy abort-session answers sent"
	::={ psmDiameterGyAbortsessionAnswersSentLevelEntry 3 }

psmDiameterGyAbortsessionAnswersSentLevelMax OBJECT-TYPE
	SYNTAX     CounterBasedGauge64
	MAX-ACCESS read-only
	STATUS     current
	DESCRIPTION
	"Gy abort-session answers sent"
	::={ psmDiameterGyAbortsessionAnswersSentLevelEntry 4 }

psmDiameterGyAbortsessionRequestsReceived OBJECT IDENTIFIER ::= { psmDiameter 10 }

psmDiameterGyAbortsessionRequestsReceivedVal OBJECT-TYPE
	SYNTAX     Counter64
	MAX-ACCESS read-only
	STATUS     current
	DESCRIPTION "Gy abort-session requests received"

	::={ psmDiameterGyAbortsessionRequestsReceived 1 }

psmDiameterGyAbortsessionRequestsReceivedMom OBJECT-TYPE
	SYNTAX     CounterBasedGauge64
	MAX-ACCESS read-only
	STATUS     current
	DESCRIPTION "Gy abort-session requests received"

	::={ psmDiameterGyAbortsessionRequestsReceived 2 }

psmDiameterGyAbortsessionRequestsReceivedMax OBJECT-TYPE
	SYNTAX     CounterBasedGauge64
	MAX-ACCESS read-only
	STATUS     current
	DESCRIPTION "Gy abort-session requests received"

	::={ psmDiameterGyAbortsessionRequestsReceived 3 }

psmDiameterGyAbortsessionRequestsReceivedLevelTable OBJECT-TYPE
	SYNTAX     SEQUENCE OF PsmDiameterGyAbortsessionRequestsReceivedLevelEntry
	MAX-ACCESS not-accessible
	STATUS     current
	DESCRIPTION
	"Gy abort-session requests received"
	::={ psmDiameterGyAbortsessionRequestsReceived 4 }

psmDiameterGyAbortsessionRequestsReceivedLevelEntry OBJECT-TYPE
	SYNTAX      PsmDiameterGyAbortsessionRequestsReceivedLevelEntry
	MAX-ACCESS  not-accessible
	STATUS      current
	DESCRIPTION
	"Gy abort-session requests received"
	INDEX { psmDiameterGyAbortsessionRequestsReceivedLevelName }
	::={ psmDiameterGyAbortsessionRequestsReceivedLevelTable 1 }

PsmDiameterGyAbortsessionRequestsReceivedLevelEntry ::=
	SEQUENCE {
		psmDiameterGyAbortsessionRequestsReceivedLevelName DisplayString,
		psmDiameterGyAbortsessionRequestsReceivedLevelVal  Counter64,
		psmDiameterGyAbortsessionRequestsReceivedLevelMom  CounterBasedGauge64,
		psmDiameterGyAbortsessionRequestsReceivedLevelMax  CounterBasedGauge64
	}

psmDiameterGyAbortsessionRequestsReceivedLevelName OBJECT-TYPE
	SYNTAX      DisplayString
	MAX-ACCESS  not-accessible
	STATUS      current
	DESCRIPTION
	"Gy abort-session requests received"
	::={ psmDiameterGyAbortsessionRequestsReceivedLevelEntry 1}

psmDiameterGyAbortsessionRequestsReceivedLevelVal OBJECT-TYPE
	SYNTAX     Counter64
	MAX-ACCESS read-only
	STATUS     current
	DESCRIPTION
	"Gy abort-session requests received"
	::={ psmDiameterGyAbortsessionRequestsReceivedLevelEntry 2 }

psmDiameterGyAbortsessionRequestsReceivedLevelMom OBJECT-TYPE
	SYNTAX     CounterBasedGauge64
	MAX-ACCESS read-only
	STATUS     current
	DESCRIPTION
	"Gy abort-session requests received"
	::={ psmDiameterGyAbortsessionRequestsReceivedLevelEntry 3 }

psmDiameterGyAbortsessionRequestsReceivedLevelMax OBJECT-TYPE
	SYNTAX     CounterBasedGauge64
	MAX-ACCESS read-only
	STATUS     current
	DESCRIPTION
	"Gy abort-session requests received"
	::={ psmDiameterGyAbortsessionRequestsReceivedLevelEntry 4 }

psmDiameterGyCreditcontrolInitialErrorAnswersReceived OBJECT IDENTIFIER ::= { psmDiameter 11 }

psmDiameterGyCreditcontrolInitialErrorAnswersReceivedVal OBJECT-TYPE
	SYNTAX     Counter64
	MAX-ACCESS read-only
	STATUS     current
	DESCRIPTION "Gy credit-control initial error answers received"

	::={ psmDiameterGyCreditcontrolInitialErrorAnswersReceived 1 }

psmDiameterGyCreditcontrolInitialErrorAnswersReceivedMom OBJECT-TYPE
	SYNTAX     CounterBasedGauge64
	MAX-ACCESS read-only
	STATUS     current
	DESCRIPTION "Gy credit-control initial error answers received"

	::={ psmDiameterGyCreditcontrolInitialErrorAnswersReceived 2 }

psmDiameterGyCreditcontrolInitialErrorAnswersReceivedMax OBJECT-TYPE
	SYNTAX     CounterBasedGauge64
	MAX-ACCESS read-only
	STATUS     current
	DESCRIPTION "Gy credit-control initial error answers received"

	::={ psmDiameterGyCreditcontrolInitialErrorAnswersReceived 3 }

psmDiameterGyCreditcontrolInitialErrorAnswersReceivedLevelTable OBJECT-TYPE
	SYNTAX     SEQUENCE OF PsmDiameterGyCreditcontrolInitialErrorAnswersReceivedLevelEntry
	MAX-ACCESS not-accessible
	STATUS     current
	DESCRIPTION
	"Gy credit-control initial error answers received"
	::={ psmDiameterGyCreditcontrolInitialErrorAnswersReceived 4 }

psmDiameterGyCreditcontrolInitialErrorAnswersReceivedLevelEntry OBJECT-TYPE
	SYNTAX      PsmDiameterGyCreditcontrolInitialErrorAnswersReceivedLevelEntry
	MAX-ACCESS  not-accessible
	STATUS      current
	DESCRIPTION
	"Gy credit-control initial error answers received"
	INDEX { psmDiameterGyCreditcontrolInitialErrorAnswersReceivedLevelName }
	::={ psmDiameterGyCreditcontrolInitialErrorAnswersReceivedLevelTable 1 }

PsmDiameterGyCreditcontrolInitialErrorAnswersReceivedLevelEntry ::=
	SEQUENCE {
		psmDiameterGyCreditcontrolInitialErrorAnswersReceivedLevelName DisplayString,
		psmDiameterGyCreditcontrolInitialErrorAnswersReceivedLevelVal  Counter64,
		psmDiameterGyCreditcontrolInitialErrorAnswersReceivedLevelMom  CounterBasedGauge64,
		psmDiameterGyCreditcontrolInitialErrorAnswersReceivedLevelMax  CounterBasedGauge64
	}

psmDiameterGyCreditcontrolInitialErrorAnswersReceivedLevelName OBJECT-TYPE
	SYNTAX      DisplayString
	MAX-ACCESS  not-accessible
	STATUS      current
	DESCRIPTION
	"Gy credit-control initial error answers received"
	::={ psmDiameterGyCreditcontrolInitialErrorAnswersReceivedLevelEntry 1}

psmDiameterGyCreditcontrolInitialErrorAnswersReceivedLevelVal OBJECT-TYPE
	SYNTAX     Counter64
	MAX-ACCESS read-only
	STATUS     current
	DESCRIPTION
	"Gy credit-control initial error answers received"
	::={ psmDiameterGyCreditcontrolInitialErrorAnswersReceivedLevelEntry 2 }

psmDiameterGyCreditcontrolInitialErrorAnswersReceivedLevelMom OBJECT-TYPE
	SYNTAX     CounterBasedGauge64
	MAX-ACCESS read-only
	STATUS     current
	DESCRIPTION
	"Gy credit-control initial error answers received"
	::={ psmDiameterGyCreditcontrolInitialErrorAnswersReceivedLevelEntry 3 }

psmDiameterGyCreditcontrolInitialErrorAnswersReceivedLevelMax OBJECT-TYPE
	SYNTAX     CounterBasedGauge64
	MAX-ACCESS read-only
	STATUS     current
	DESCRIPTION
	"Gy credit-control initial error answers received"
	::={ psmDiameterGyCreditcontrolInitialErrorAnswersReceivedLevelEntry 4 }

psmDiameterGyCreditcontrolInitialAnswerHandlingFailures OBJECT IDENTIFIER ::= { psmDiameter 12 }

psmDiameterGyCreditcontrolInitialAnswerHandlingFailuresVal OBJECT-TYPE
	SYNTAX     Counter64
	MAX-ACCESS read-only
	STATUS     current
	DESCRIPTION "Gy credit-control initial answer handling failures"

	::={ psmDiameterGyCreditcontrolInitialAnswerHandlingFailures 1 }

psmDiameterGyCreditcontrolInitialAnswerHandlingFailuresMom OBJECT-TYPE
	SYNTAX     CounterBasedGauge64
	MAX-ACCESS read-only
	STATUS     current
	DESCRIPTION "Gy credit-control initial answer handling failures"

	::={ psmDiameterGyCreditcontrolInitialAnswerHandlingFailures 2 }

psmDiameterGyCreditcontrolInitialAnswerHandlingFailuresMax OBJECT-TYPE
	SYNTAX     CounterBasedGauge64
	MAX-ACCESS read-only
	STATUS     current
	DESCRIPTION "Gy credit-control initial answer handling failures"

	::={ psmDiameterGyCreditcontrolInitialAnswerHandlingFailures 3 }

psmDiameterGyCreditcontrolInitialAnswerHandlingFailuresLevelTable OBJECT-TYPE
	SYNTAX     SEQUENCE OF PsmDiameterGyCreditcontrolInitialAnswerHandlingFailuresLevelEntry
	MAX-ACCESS not-accessible
	STATUS     current
	DESCRIPTION
	"Gy credit-control initial answer handling failures"
	::={ psmDiameterGyCreditcontrolInitialAnswerHandlingFailures 4 }

psmDiameterGyCreditcontrolInitialAnswerHandlingFailuresLevelEntry OBJECT-TYPE
	SYNTAX      PsmDiameterGyCreditcontrolInitialAnswerHandlingFailuresLevelEntry
	MAX-ACCESS  not-accessible
	STATUS      current
	DESCRIPTION
	"Gy credit-control initial answer handling failures"
	INDEX { psmDiameterGyCreditcontrolInitialAnswerHandlingFailuresLevelName }
	::={ psmDiameterGyCreditcontrolInitialAnswerHandlingFailuresLevelTable 1 }

PsmDiameterGyCreditcontrolInitialAnswerHandlingFailuresLevelEntry ::=
	SEQUENCE {
		psmDiameterGyCreditcontrolInitialAnswerHandlingFailuresLevelName DisplayString,
		psmDiameterGyCreditcontrolInitialAnswerHandlingFailuresLevelVal  Counter64,
		psmDiameterGyCreditcontrolInitialAnswerHandlingFailuresLevelMom  CounterBasedGauge64,
		psmDiameterGyCreditcontrolInitialAnswerHandlingFailuresLevelMax  CounterBasedGauge64
	}

psmDiameterGyCreditcontrolInitialAnswerHandlingFailuresLevelName OBJECT-TYPE
	SYNTAX      DisplayString
	MAX-ACCESS  not-accessible
	STATUS      current
	DESCRIPTION
	"Gy credit-control initial answer handling failures"
	::={ psmDiameterGyCreditcontrolInitialAnswerHandlingFailuresLevelEntry 1}

psmDiameterGyCreditcontrolInitialAnswerHandlingFailuresLevelVal OBJECT-TYPE
	SYNTAX     Counter64
	MAX-ACCESS read-only
	STATUS     current
	DESCRIPTION
	"Gy credit-control initial answer handling failures"
	::={ psmDiameterGyCreditcontrolInitialAnswerHandlingFailuresLevelEntry 2 }

psmDiameterGyCreditcontrolInitialAnswerHandlingFailuresLevelMom OBJECT-TYPE
	SYNTAX     CounterBasedGauge64
	MAX-ACCESS read-only
	STATUS     current
	DESCRIPTION
	"Gy credit-control initial answer handling failures"
	::={ psmDiameterGyCreditcontrolInitialAnswerHandlingFailuresLevelEntry 3 }

psmDiameterGyCreditcontrolInitialAnswerHandlingFailuresLevelMax OBJECT-TYPE
	SYNTAX     CounterBasedGauge64
	MAX-ACCESS read-only
	STATUS     current
	DESCRIPTION
	"Gy credit-control initial answer handling failures"
	::={ psmDiameterGyCreditcontrolInitialAnswerHandlingFailuresLevelEntry 4 }

psmDiameterGyCreditcontrolInitialAnswersReceived OBJECT IDENTIFIER ::= { psmDiameter 13 }

psmDiameterGyCreditcontrolInitialAnswersReceivedVal OBJECT-TYPE
	SYNTAX     Counter64
	MAX-ACCESS read-only
	STATUS     current
	DESCRIPTION "Gy credit-control initial answers received"

	::={ psmDiameterGyCreditcontrolInitialAnswersReceived 1 }

psmDiameterGyCreditcontrolInitialAnswersReceivedMom OBJECT-TYPE
	SYNTAX     CounterBasedGauge64
	MAX-ACCESS read-only
	STATUS     current
	DESCRIPTION "Gy credit-control initial answers received"

	::={ psmDiameterGyCreditcontrolInitialAnswersReceived 2 }

psmDiameterGyCreditcontrolInitialAnswersReceivedMax OBJECT-TYPE
	SYNTAX     CounterBasedGauge64
	MAX-ACCESS read-only
	STATUS     current
	DESCRIPTION "Gy credit-control initial answers received"

	::={ psmDiameterGyCreditcontrolInitialAnswersReceived 3 }

psmDiameterGyCreditcontrolInitialAnswersReceivedLevelTable OBJECT-TYPE
	SYNTAX     SEQUENCE OF PsmDiameterGyCreditcontrolInitialAnswersReceivedLevelEntry
	MAX-ACCESS not-accessible
	STATUS     current
	DESCRIPTION
	"Gy credit-control initial answers received"
	::={ psmDiameterGyCreditcontrolInitialAnswersReceived 4 }

psmDiameterGyCreditcontrolInitialAnswersReceivedLevelEntry OBJECT-TYPE
	SYNTAX      PsmDiameterGyCreditcontrolInitialAnswersReceivedLevelEntry
	MAX-ACCESS  not-accessible
	STATUS      current
	DESCRIPTION
	"Gy credit-control initial answers received"
	INDEX { psmDiameterGyCreditcontrolInitialAnswersReceivedLevelName }
	::={ psmDiameterGyCreditcontrolInitialAnswersReceivedLevelTable 1 }

PsmDiameterGyCreditcontrolInitialAnswersReceivedLevelEntry ::=
	SEQUENCE {
		psmDiameterGyCreditcontrolInitialAnswersReceivedLevelName DisplayString,
		psmDiameterGyCreditcontrolInitialAnswersReceivedLevelVal  Counter64,
		psmDiameterGyCreditcontrolInitialAnswersReceivedLevelMom  CounterBasedGauge64,
		psmDiameterGyCreditcontrolInitialAnswersReceivedLevelMax  CounterBasedGauge64
	}

psmDiameterGyCreditcontrolInitialAnswersReceivedLevelName OBJECT-TYPE
	SYNTAX      DisplayString
	MAX-ACCESS  not-accessible
	STATUS      current
	DESCRIPTION
	"Gy credit-control initial answers received"
	::={ psmDiameterGyCreditcontrolInitialAnswersReceivedLevelEntry 1}

psmDiameterGyCreditcontrolInitialAnswersReceivedLevelVal OBJECT-TYPE
	SYNTAX     Counter64
	MAX-ACCESS read-only
	STATUS     current
	DESCRIPTION
	"Gy credit-control initial answers received"
	::={ psmDiameterGyCreditcontrolInitialAnswersReceivedLevelEntry 2 }

psmDiameterGyCreditcontrolInitialAnswersReceivedLevelMom OBJECT-TYPE
	SYNTAX     CounterBasedGauge64
	MAX-ACCESS read-only
	STATUS     current
	DESCRIPTION
	"Gy credit-control initial answers received"
	::={ psmDiameterGyCreditcontrolInitialAnswersReceivedLevelEntry 3 }

psmDiameterGyCreditcontrolInitialAnswersReceivedLevelMax OBJECT-TYPE
	SYNTAX     CounterBasedGauge64
	MAX-ACCESS read-only
	STATUS     current
	DESCRIPTION
	"Gy credit-control initial answers received"
	::={ psmDiameterGyCreditcontrolInitialAnswersReceivedLevelEntry 4 }

psmDiameterGyCreditcontrolTerminateErrorAnswersReceived OBJECT IDENTIFIER ::= { psmDiameter 14 }

psmDiameterGyCreditcontrolTerminateErrorAnswersReceivedVal OBJECT-TYPE
	SYNTAX     Counter64
	MAX-ACCESS read-only
	STATUS     current
	DESCRIPTION "Gy credit-control terminate error answers received"

	::={ psmDiameterGyCreditcontrolTerminateErrorAnswersReceived 1 }

psmDiameterGyCreditcontrolTerminateErrorAnswersReceivedMom OBJECT-TYPE
	SYNTAX     CounterBasedGauge64
	MAX-ACCESS read-only
	STATUS     current
	DESCRIPTION "Gy credit-control terminate error answers received"

	::={ psmDiameterGyCreditcontrolTerminateErrorAnswersReceived 2 }

psmDiameterGyCreditcontrolTerminateErrorAnswersReceivedMax OBJECT-TYPE
	SYNTAX     CounterBasedGauge64
	MAX-ACCESS read-only
	STATUS     current
	DESCRIPTION "Gy credit-control terminate error answers received"

	::={ psmDiameterGyCreditcontrolTerminateErrorAnswersReceived 3 }

psmDiameterGyCreditcontrolTerminateErrorAnswersReceivedLevelTable OBJECT-TYPE
	SYNTAX     SEQUENCE OF PsmDiameterGyCreditcontrolTerminateErrorAnswersReceivedLevelEntry
	MAX-ACCESS not-accessible
	STATUS     current
	DESCRIPTION
	"Gy credit-control terminate error answers received"
	::={ psmDiameterGyCreditcontrolTerminateErrorAnswersReceived 4 }

psmDiameterGyCreditcontrolTerminateErrorAnswersReceivedLevelEntry OBJECT-TYPE
	SYNTAX      PsmDiameterGyCreditcontrolTerminateErrorAnswersReceivedLevelEntry
	MAX-ACCESS  not-accessible
	STATUS      current
	DESCRIPTION
	"Gy credit-control terminate error answers received"
	INDEX { psmDiameterGyCreditcontrolTerminateErrorAnswersReceivedLevelName }
	::={ psmDiameterGyCreditcontrolTerminateErrorAnswersReceivedLevelTable 1 }

PsmDiameterGyCreditcontrolTerminateErrorAnswersReceivedLevelEntry ::=
	SEQUENCE {
		psmDiameterGyCreditcontrolTerminateErrorAnswersReceivedLevelName DisplayString,
		psmDiameterGyCreditcontrolTerminateErrorAnswersReceivedLevelVal  Counter64,
		psmDiameterGyCreditcontrolTerminateErrorAnswersReceivedLevelMom  CounterBasedGauge64,
		psmDiameterGyCreditcontrolTerminateErrorAnswersReceivedLevelMax  CounterBasedGauge64
	}

psmDiameterGyCreditcontrolTerminateErrorAnswersReceivedLevelName OBJECT-TYPE
	SYNTAX      DisplayString
	MAX-ACCESS  not-accessible
	STATUS      current
	DESCRIPTION
	"Gy credit-control terminate error answers received"
	::={ psmDiameterGyCreditcontrolTerminateErrorAnswersReceivedLevelEntry 1}

psmDiameterGyCreditcontrolTerminateErrorAnswersReceivedLevelVal OBJECT-TYPE
	SYNTAX     Counter64
	MAX-ACCESS read-only
	STATUS     current
	DESCRIPTION
	"Gy credit-control terminate error answers received"
	::={ psmDiameterGyCreditcontrolTerminateErrorAnswersReceivedLevelEntry 2 }

psmDiameterGyCreditcontrolTerminateErrorAnswersReceivedLevelMom OBJECT-TYPE
	SYNTAX     CounterBasedGauge64
	MAX-ACCESS read-only
	STATUS     current
	DESCRIPTION
	"Gy credit-control terminate error answers received"
	::={ psmDiameterGyCreditcontrolTerminateErrorAnswersReceivedLevelEntry 3 }

psmDiameterGyCreditcontrolTerminateErrorAnswersReceivedLevelMax OBJECT-TYPE
	SYNTAX     CounterBasedGauge64
	MAX-ACCESS read-only
	STATUS     current
	DESCRIPTION
	"Gy credit-control terminate error answers received"
	::={ psmDiameterGyCreditcontrolTerminateErrorAnswersReceivedLevelEntry 4 }

psmDiameterGyCreditcontrolTerminateAnswerHandlingFailures OBJECT IDENTIFIER ::= { psmDiameter 15 }

psmDiameterGyCreditcontrolTerminateAnswerHandlingFailuresVal OBJECT-TYPE
	SYNTAX     Counter64
	MAX-ACCESS read-only
	STATUS     current
	DESCRIPTION "Gy credit-control terminate answer handling failures"

	::={ psmDiameterGyCreditcontrolTerminateAnswerHandlingFailures 1 }

psmDiameterGyCreditcontrolTerminateAnswerHandlingFailuresMom OBJECT-TYPE
	SYNTAX     CounterBasedGauge64
	MAX-ACCESS read-only
	STATUS     current
	DESCRIPTION "Gy credit-control terminate answer handling failures"

	::={ psmDiameterGyCreditcontrolTerminateAnswerHandlingFailures 2 }

psmDiameterGyCreditcontrolTerminateAnswerHandlingFailuresMax OBJECT-TYPE
	SYNTAX     CounterBasedGauge64
	MAX-ACCESS read-only
	STATUS     current
	DESCRIPTION "Gy credit-control terminate answer handling failures"

	::={ psmDiameterGyCreditcontrolTerminateAnswerHandlingFailures 3 }

psmDiameterGyCreditcontrolTerminateAnswerHandlingFailuresLevelTable OBJECT-TYPE
	SYNTAX     SEQUENCE OF PsmDiameterGyCreditcontrolTerminateAnswerHandlingFailuresLevelEntry
	MAX-ACCESS not-accessible
	STATUS     current
	DESCRIPTION
	"Gy credit-control terminate answer handling failures"
	::={ psmDiameterGyCreditcontrolTerminateAnswerHandlingFailures 4 }

psmDiameterGyCreditcontrolTerminateAnswerHandlingFailuresLevelEntry OBJECT-TYPE
	SYNTAX      PsmDiameterGyCreditcontrolTerminateAnswerHandlingFailuresLevelEntry
	MAX-ACCESS  not-accessible
	STATUS      current
	DESCRIPTION
	"Gy credit-control terminate answer handling failures"
	INDEX { psmDiameterGyCreditcontrolTerminateAnswerHandlingFailuresLevelName }
	::={ psmDiameterGyCreditcontrolTerminateAnswerHandlingFailuresLevelTable 1 }

PsmDiameterGyCreditcontrolTerminateAnswerHandlingFailuresLevelEntry ::=
	SEQUENCE {
		psmDiameterGyCreditcontrolTerminateAnswerHandlingFailuresLevelName DisplayString,
		psmDiameterGyCreditcontrolTerminateAnswerHandlingFailuresLevelVal  Counter64,
		psmDiameterGyCreditcontrolTerminateAnswerHandlingFailuresLevelMom  CounterBasedGauge64,
		psmDiameterGyCreditcontrolTerminateAnswerHandlingFailuresLevelMax  CounterBasedGauge64
	}

psmDiameterGyCreditcontrolTerminateAnswerHandlingFailuresLevelName OBJECT-TYPE
	SYNTAX      DisplayString
	MAX-ACCESS  not-accessible
	STATUS      current
	DESCRIPTION
	"Gy credit-control terminate answer handling failures"
	::={ psmDiameterGyCreditcontrolTerminateAnswerHandlingFailuresLevelEntry 1}

psmDiameterGyCreditcontrolTerminateAnswerHandlingFailuresLevelVal OBJECT-TYPE
	SYNTAX     Counter64
	MAX-ACCESS read-only
	STATUS     current
	DESCRIPTION
	"Gy credit-control terminate answer handling failures"
	::={ psmDiameterGyCreditcontrolTerminateAnswerHandlingFailuresLevelEntry 2 }

psmDiameterGyCreditcontrolTerminateAnswerHandlingFailuresLevelMom OBJECT-TYPE
	SYNTAX     CounterBasedGauge64
	MAX-ACCESS read-only
	STATUS     current
	DESCRIPTION
	"Gy credit-control terminate answer handling failures"
	::={ psmDiameterGyCreditcontrolTerminateAnswerHandlingFailuresLevelEntry 3 }

psmDiameterGyCreditcontrolTerminateAnswerHandlingFailuresLevelMax OBJECT-TYPE
	SYNTAX     CounterBasedGauge64
	MAX-ACCESS read-only
	STATUS     current
	DESCRIPTION
	"Gy credit-control terminate answer handling failures"
	::={ psmDiameterGyCreditcontrolTerminateAnswerHandlingFailuresLevelEntry 4 }

psmDiameterGyCreditcontrolTerminateAnswersReceived OBJECT IDENTIFIER ::= { psmDiameter 16 }

psmDiameterGyCreditcontrolTerminateAnswersReceivedVal OBJECT-TYPE
	SYNTAX     Counter64
	MAX-ACCESS read-only
	STATUS     current
	DESCRIPTION "Gy credit-control terminate answers received"

	::={ psmDiameterGyCreditcontrolTerminateAnswersReceived 1 }

psmDiameterGyCreditcontrolTerminateAnswersReceivedMom OBJECT-TYPE
	SYNTAX     CounterBasedGauge64
	MAX-ACCESS read-only
	STATUS     current
	DESCRIPTION "Gy credit-control terminate answers received"

	::={ psmDiameterGyCreditcontrolTerminateAnswersReceived 2 }

psmDiameterGyCreditcontrolTerminateAnswersReceivedMax OBJECT-TYPE
	SYNTAX     CounterBasedGauge64
	MAX-ACCESS read-only
	STATUS     current
	DESCRIPTION "Gy credit-control terminate answers received"

	::={ psmDiameterGyCreditcontrolTerminateAnswersReceived 3 }

psmDiameterGyCreditcontrolTerminateAnswersReceivedLevelTable OBJECT-TYPE
	SYNTAX     SEQUENCE OF PsmDiameterGyCreditcontrolTerminateAnswersReceivedLevelEntry
	MAX-ACCESS not-accessible
	STATUS     current
	DESCRIPTION
	"Gy credit-control terminate answers received"
	::={ psmDiameterGyCreditcontrolTerminateAnswersReceived 4 }

psmDiameterGyCreditcontrolTerminateAnswersReceivedLevelEntry OBJECT-TYPE
	SYNTAX      PsmDiameterGyCreditcontrolTerminateAnswersReceivedLevelEntry
	MAX-ACCESS  not-accessible
	STATUS      current
	DESCRIPTION
	"Gy credit-control terminate answers received"
	INDEX { psmDiameterGyCreditcontrolTerminateAnswersReceivedLevelName }
	::={ psmDiameterGyCreditcontrolTerminateAnswersReceivedLevelTable 1 }

PsmDiameterGyCreditcontrolTerminateAnswersReceivedLevelEntry ::=
	SEQUENCE {
		psmDiameterGyCreditcontrolTerminateAnswersReceivedLevelName DisplayString,
		psmDiameterGyCreditcontrolTerminateAnswersReceivedLevelVal  Counter64,
		psmDiameterGyCreditcontrolTerminateAnswersReceivedLevelMom  CounterBasedGauge64,
		psmDiameterGyCreditcontrolTerminateAnswersReceivedLevelMax  CounterBasedGauge64
	}

psmDiameterGyCreditcontrolTerminateAnswersReceivedLevelName OBJECT-TYPE
	SYNTAX      DisplayString
	MAX-ACCESS  not-accessible
	STATUS      current
	DESCRIPTION
	"Gy credit-control terminate answers received"
	::={ psmDiameterGyCreditcontrolTerminateAnswersReceivedLevelEntry 1}

psmDiameterGyCreditcontrolTerminateAnswersReceivedLevelVal OBJECT-TYPE
	SYNTAX     Counter64
	MAX-ACCESS read-only
	STATUS     current
	DESCRIPTION
	"Gy credit-control terminate answers received"
	::={ psmDiameterGyCreditcontrolTerminateAnswersReceivedLevelEntry 2 }

psmDiameterGyCreditcontrolTerminateAnswersReceivedLevelMom OBJECT-TYPE
	SYNTAX     CounterBasedGauge64
	MAX-ACCESS read-only
	STATUS     current
	DESCRIPTION
	"Gy credit-control terminate answers received"
	::={ psmDiameterGyCreditcontrolTerminateAnswersReceivedLevelEntry 3 }

psmDiameterGyCreditcontrolTerminateAnswersReceivedLevelMax OBJECT-TYPE
	SYNTAX     CounterBasedGauge64
	MAX-ACCESS read-only
	STATUS     current
	DESCRIPTION
	"Gy credit-control terminate answers received"
	::={ psmDiameterGyCreditcontrolTerminateAnswersReceivedLevelEntry 4 }

psmDiameterGyCreditcontrolUpdateErrorAnswersReceived OBJECT IDENTIFIER ::= { psmDiameter 17 }

psmDiameterGyCreditcontrolUpdateErrorAnswersReceivedVal OBJECT-TYPE
	SYNTAX     Counter64
	MAX-ACCESS read-only
	STATUS     current
	DESCRIPTION "Gy credit-control update error answers received"

	::={ psmDiameterGyCreditcontrolUpdateErrorAnswersReceived 1 }

psmDiameterGyCreditcontrolUpdateErrorAnswersReceivedMom OBJECT-TYPE
	SYNTAX     CounterBasedGauge64
	MAX-ACCESS read-only
	STATUS     current
	DESCRIPTION "Gy credit-control update error answers received"

	::={ psmDiameterGyCreditcontrolUpdateErrorAnswersReceived 2 }

psmDiameterGyCreditcontrolUpdateErrorAnswersReceivedMax OBJECT-TYPE
	SYNTAX     CounterBasedGauge64
	MAX-ACCESS read-only
	STATUS     current
	DESCRIPTION "Gy credit-control update error answers received"

	::={ psmDiameterGyCreditcontrolUpdateErrorAnswersReceived 3 }

psmDiameterGyCreditcontrolUpdateErrorAnswersReceivedLevelTable OBJECT-TYPE
	SYNTAX     SEQUENCE OF PsmDiameterGyCreditcontrolUpdateErrorAnswersReceivedLevelEntry
	MAX-ACCESS not-accessible
	STATUS     current
	DESCRIPTION
	"Gy credit-control update error answers received"
	::={ psmDiameterGyCreditcontrolUpdateErrorAnswersReceived 4 }

psmDiameterGyCreditcontrolUpdateErrorAnswersReceivedLevelEntry OBJECT-TYPE
	SYNTAX      PsmDiameterGyCreditcontrolUpdateErrorAnswersReceivedLevelEntry
	MAX-ACCESS  not-accessible
	STATUS      current
	DESCRIPTION
	"Gy credit-control update error answers received"
	INDEX { psmDiameterGyCreditcontrolUpdateErrorAnswersReceivedLevelName }
	::={ psmDiameterGyCreditcontrolUpdateErrorAnswersReceivedLevelTable 1 }

PsmDiameterGyCreditcontrolUpdateErrorAnswersReceivedLevelEntry ::=
	SEQUENCE {
		psmDiameterGyCreditcontrolUpdateErrorAnswersReceivedLevelName DisplayString,
		psmDiameterGyCreditcontrolUpdateErrorAnswersReceivedLevelVal  Counter64,
		psmDiameterGyCreditcontrolUpdateErrorAnswersReceivedLevelMom  CounterBasedGauge64,
		psmDiameterGyCreditcontrolUpdateErrorAnswersReceivedLevelMax  CounterBasedGauge64
	}

psmDiameterGyCreditcontrolUpdateErrorAnswersReceivedLevelName OBJECT-TYPE
	SYNTAX      DisplayString
	MAX-ACCESS  not-accessible
	STATUS      current
	DESCRIPTION
	"Gy credit-control update error answers received"
	::={ psmDiameterGyCreditcontrolUpdateErrorAnswersReceivedLevelEntry 1}

psmDiameterGyCreditcontrolUpdateErrorAnswersReceivedLevelVal OBJECT-TYPE
	SYNTAX     Counter64
	MAX-ACCESS read-only
	STATUS     current
	DESCRIPTION
	"Gy credit-control update error answers received"
	::={ psmDiameterGyCreditcontrolUpdateErrorAnswersReceivedLevelEntry 2 }

psmDiameterGyCreditcontrolUpdateErrorAnswersReceivedLevelMom OBJECT-TYPE
	SYNTAX     CounterBasedGauge64
	MAX-ACCESS read-only
	STATUS     current
	DESCRIPTION
	"Gy credit-control update error answers received"
	::={ psmDiameterGyCreditcontrolUpdateErrorAnswersReceivedLevelEntry 3 }

psmDiameterGyCreditcontrolUpdateErrorAnswersReceivedLevelMax OBJECT-TYPE
	SYNTAX     CounterBasedGauge64
	MAX-ACCESS read-only
	STATUS     current
	DESCRIPTION
	"Gy credit-control update error answers received"
	::={ psmDiameterGyCreditcontrolUpdateErrorAnswersReceivedLevelEntry 4 }

psmDiameterGyCreditcontrolUpdateAnswerHandlingFailures OBJECT IDENTIFIER ::= { psmDiameter 18 }

psmDiameterGyCreditcontrolUpdateAnswerHandlingFailuresVal OBJECT-TYPE
	SYNTAX     Counter64
	MAX-ACCESS read-only
	STATUS     current
	DESCRIPTION "Gy credit-control update answer handling failures"

	::={ psmDiameterGyCreditcontrolUpdateAnswerHandlingFailures 1 }

psmDiameterGyCreditcontrolUpdateAnswerHandlingFailuresMom OBJECT-TYPE
	SYNTAX     CounterBasedGauge64
	MAX-ACCESS read-only
	STATUS     current
	DESCRIPTION "Gy credit-control update answer handling failures"

	::={ psmDiameterGyCreditcontrolUpdateAnswerHandlingFailures 2 }

psmDiameterGyCreditcontrolUpdateAnswerHandlingFailuresMax OBJECT-TYPE
	SYNTAX     CounterBasedGauge64
	MAX-ACCESS read-only
	STATUS     current
	DESCRIPTION "Gy credit-control update answer handling failures"

	::={ psmDiameterGyCreditcontrolUpdateAnswerHandlingFailures 3 }

psmDiameterGyCreditcontrolUpdateAnswerHandlingFailuresLevelTable OBJECT-TYPE
	SYNTAX     SEQUENCE OF PsmDiameterGyCreditcontrolUpdateAnswerHandlingFailuresLevelEntry
	MAX-ACCESS not-accessible
	STATUS     current
	DESCRIPTION
	"Gy credit-control update answer handling failures"
	::={ psmDiameterGyCreditcontrolUpdateAnswerHandlingFailures 4 }

psmDiameterGyCreditcontrolUpdateAnswerHandlingFailuresLevelEntry OBJECT-TYPE
	SYNTAX      PsmDiameterGyCreditcontrolUpdateAnswerHandlingFailuresLevelEntry
	MAX-ACCESS  not-accessible
	STATUS      current
	DESCRIPTION
	"Gy credit-control update answer handling failures"
	INDEX { psmDiameterGyCreditcontrolUpdateAnswerHandlingFailuresLevelName }
	::={ psmDiameterGyCreditcontrolUpdateAnswerHandlingFailuresLevelTable 1 }

PsmDiameterGyCreditcontrolUpdateAnswerHandlingFailuresLevelEntry ::=
	SEQUENCE {
		psmDiameterGyCreditcontrolUpdateAnswerHandlingFailuresLevelName DisplayString,
		psmDiameterGyCreditcontrolUpdateAnswerHandlingFailuresLevelVal  Counter64,
		psmDiameterGyCreditcontrolUpdateAnswerHandlingFailuresLevelMom  CounterBasedGauge64,
		psmDiameterGyCreditcontrolUpdateAnswerHandlingFailuresLevelMax  CounterBasedGauge64
	}

psmDiameterGyCreditcontrolUpdateAnswerHandlingFailuresLevelName OBJECT-TYPE
	SYNTAX      DisplayString
	MAX-ACCESS  not-accessible
	STATUS      current
	DESCRIPTION
	"Gy credit-control update answer handling failures"
	::={ psmDiameterGyCreditcontrolUpdateAnswerHandlingFailuresLevelEntry 1}

psmDiameterGyCreditcontrolUpdateAnswerHandlingFailuresLevelVal OBJECT-TYPE
	SYNTAX     Counter64
	MAX-ACCESS read-only
	STATUS     current
	DESCRIPTION
	"Gy credit-control update answer handling failures"
	::={ psmDiameterGyCreditcontrolUpdateAnswerHandlingFailuresLevelEntry 2 }

psmDiameterGyCreditcontrolUpdateAnswerHandlingFailuresLevelMom OBJECT-TYPE
	SYNTAX     CounterBasedGauge64
	MAX-ACCESS read-only
	STATUS     current
	DESCRIPTION
	"Gy credit-control update answer handling failures"
	::={ psmDiameterGyCreditcontrolUpdateAnswerHandlingFailuresLevelEntry 3 }

psmDiameterGyCreditcontrolUpdateAnswerHandlingFailuresLevelMax OBJECT-TYPE
	SYNTAX     CounterBasedGauge64
	MAX-ACCESS read-only
	STATUS     current
	DESCRIPTION
	"Gy credit-control update answer handling failures"
	::={ psmDiameterGyCreditcontrolUpdateAnswerHandlingFailuresLevelEntry 4 }

psmDiameterGyCreditcontrolUpdateAnswersReceived OBJECT IDENTIFIER ::= { psmDiameter 19 }

psmDiameterGyCreditcontrolUpdateAnswersReceivedVal OBJECT-TYPE
	SYNTAX     Counter64
	MAX-ACCESS read-only
	STATUS     current
	DESCRIPTION "Gy credit-control update answers received"

	::={ psmDiameterGyCreditcontrolUpdateAnswersReceived 1 }

psmDiameterGyCreditcontrolUpdateAnswersReceivedMom OBJECT-TYPE
	SYNTAX     CounterBasedGauge64
	MAX-ACCESS read-only
	STATUS     current
	DESCRIPTION "Gy credit-control update answers received"

	::={ psmDiameterGyCreditcontrolUpdateAnswersReceived 2 }

psmDiameterGyCreditcontrolUpdateAnswersReceivedMax OBJECT-TYPE
	SYNTAX     CounterBasedGauge64
	MAX-ACCESS read-only
	STATUS     current
	DESCRIPTION "Gy credit-control update answers received"

	::={ psmDiameterGyCreditcontrolUpdateAnswersReceived 3 }

psmDiameterGyCreditcontrolUpdateAnswersReceivedLevelTable OBJECT-TYPE
	SYNTAX     SEQUENCE OF PsmDiameterGyCreditcontrolUpdateAnswersReceivedLevelEntry
	MAX-ACCESS not-accessible
	STATUS     current
	DESCRIPTION
	"Gy credit-control update answers received"
	::={ psmDiameterGyCreditcontrolUpdateAnswersReceived 4 }

psmDiameterGyCreditcontrolUpdateAnswersReceivedLevelEntry OBJECT-TYPE
	SYNTAX      PsmDiameterGyCreditcontrolUpdateAnswersReceivedLevelEntry
	MAX-ACCESS  not-accessible
	STATUS      current
	DESCRIPTION
	"Gy credit-control update answers received"
	INDEX { psmDiameterGyCreditcontrolUpdateAnswersReceivedLevelName }
	::={ psmDiameterGyCreditcontrolUpdateAnswersReceivedLevelTable 1 }

PsmDiameterGyCreditcontrolUpdateAnswersReceivedLevelEntry ::=
	SEQUENCE {
		psmDiameterGyCreditcontrolUpdateAnswersReceivedLevelName DisplayString,
		psmDiameterGyCreditcontrolUpdateAnswersReceivedLevelVal  Counter64,
		psmDiameterGyCreditcontrolUpdateAnswersReceivedLevelMom  CounterBasedGauge64,
		psmDiameterGyCreditcontrolUpdateAnswersReceivedLevelMax  CounterBasedGauge64
	}

psmDiameterGyCreditcontrolUpdateAnswersReceivedLevelName OBJECT-TYPE
	SYNTAX      DisplayString
	MAX-ACCESS  not-accessible
	STATUS      current
	DESCRIPTION
	"Gy credit-control update answers received"
	::={ psmDiameterGyCreditcontrolUpdateAnswersReceivedLevelEntry 1}

psmDiameterGyCreditcontrolUpdateAnswersReceivedLevelVal OBJECT-TYPE
	SYNTAX     Counter64
	MAX-ACCESS read-only
	STATUS     current
	DESCRIPTION
	"Gy credit-control update answers received"
	::={ psmDiameterGyCreditcontrolUpdateAnswersReceivedLevelEntry 2 }

psmDiameterGyCreditcontrolUpdateAnswersReceivedLevelMom OBJECT-TYPE
	SYNTAX     CounterBasedGauge64
	MAX-ACCESS read-only
	STATUS     current
	DESCRIPTION
	"Gy credit-control update answers received"
	::={ psmDiameterGyCreditcontrolUpdateAnswersReceivedLevelEntry 3 }

psmDiameterGyCreditcontrolUpdateAnswersReceivedLevelMax OBJECT-TYPE
	SYNTAX     CounterBasedGauge64
	MAX-ACCESS read-only
	STATUS     current
	DESCRIPTION
	"Gy credit-control update answers received"
	::={ psmDiameterGyCreditcontrolUpdateAnswersReceivedLevelEntry 4 }

psmDiameterGyCreditcontrolInitialRequestsSent OBJECT IDENTIFIER ::= { psmDiameter 20 }

psmDiameterGyCreditcontrolInitialRequestsSentVal OBJECT-TYPE
	SYNTAX     Counter64
	MAX-ACCESS read-only
	STATUS     current
	DESCRIPTION "Gy credit-control initial requests sent"

	::={ psmDiameterGyCreditcontrolInitialRequestsSent 1 }

psmDiameterGyCreditcontrolInitialRequestsSentMom OBJECT-TYPE
	SYNTAX     CounterBasedGauge64
	MAX-ACCESS read-only
	STATUS     current
	DESCRIPTION "Gy credit-control initial requests sent"

	::={ psmDiameterGyCreditcontrolInitialRequestsSent 2 }

psmDiameterGyCreditcontrolInitialRequestsSentMax OBJECT-TYPE
	SYNTAX     CounterBasedGauge64
	MAX-ACCESS read-only
	STATUS     current
	DESCRIPTION "Gy credit-control initial requests sent"

	::={ psmDiameterGyCreditcontrolInitialRequestsSent 3 }

psmDiameterGyCreditcontrolInitialRequestsSentLevelTable OBJECT-TYPE
	SYNTAX     SEQUENCE OF PsmDiameterGyCreditcontrolInitialRequestsSentLevelEntry
	MAX-ACCESS not-accessible
	STATUS     current
	DESCRIPTION
	"Gy credit-control initial requests sent"
	::={ psmDiameterGyCreditcontrolInitialRequestsSent 4 }

psmDiameterGyCreditcontrolInitialRequestsSentLevelEntry OBJECT-TYPE
	SYNTAX      PsmDiameterGyCreditcontrolInitialRequestsSentLevelEntry
	MAX-ACCESS  not-accessible
	STATUS      current
	DESCRIPTION
	"Gy credit-control initial requests sent"
	INDEX { psmDiameterGyCreditcontrolInitialRequestsSentLevelName }
	::={ psmDiameterGyCreditcontrolInitialRequestsSentLevelTable 1 }

PsmDiameterGyCreditcontrolInitialRequestsSentLevelEntry ::=
	SEQUENCE {
		psmDiameterGyCreditcontrolInitialRequestsSentLevelName DisplayString,
		psmDiameterGyCreditcontrolInitialRequestsSentLevelVal  Counter64,
		psmDiameterGyCreditcontrolInitialRequestsSentLevelMom  CounterBasedGauge64,
		psmDiameterGyCreditcontrolInitialRequestsSentLevelMax  CounterBasedGauge64
	}

psmDiameterGyCreditcontrolInitialRequestsSentLevelName OBJECT-TYPE
	SYNTAX      DisplayString
	MAX-ACCESS  not-accessible
	STATUS      current
	DESCRIPTION
	"Gy credit-control initial requests sent"
	::={ psmDiameterGyCreditcontrolInitialRequestsSentLevelEntry 1}

psmDiameterGyCreditcontrolInitialRequestsSentLevelVal OBJECT-TYPE
	SYNTAX     Counter64
	MAX-ACCESS read-only
	STATUS     current
	DESCRIPTION
	"Gy credit-control initial requests sent"
	::={ psmDiameterGyCreditcontrolInitialRequestsSentLevelEntry 2 }

psmDiameterGyCreditcontrolInitialRequestsSentLevelMom OBJECT-TYPE
	SYNTAX     CounterBasedGauge64
	MAX-ACCESS read-only
	STATUS     current
	DESCRIPTION
	"Gy credit-control initial requests sent"
	::={ psmDiameterGyCreditcontrolInitialRequestsSentLevelEntry 3 }

psmDiameterGyCreditcontrolInitialRequestsSentLevelMax OBJECT-TYPE
	SYNTAX     CounterBasedGauge64
	MAX-ACCESS read-only
	STATUS     current
	DESCRIPTION
	"Gy credit-control initial requests sent"
	::={ psmDiameterGyCreditcontrolInitialRequestsSentLevelEntry 4 }

psmDiameterGyCreditcontrolTerminateRequestsSent OBJECT IDENTIFIER ::= { psmDiameter 21 }

psmDiameterGyCreditcontrolTerminateRequestsSentVal OBJECT-TYPE
	SYNTAX     Counter64
	MAX-ACCESS read-only
	STATUS     current
	DESCRIPTION "Gy credit-control terminate requests sent"

	::={ psmDiameterGyCreditcontrolTerminateRequestsSent 1 }

psmDiameterGyCreditcontrolTerminateRequestsSentMom OBJECT-TYPE
	SYNTAX     CounterBasedGauge64
	MAX-ACCESS read-only
	STATUS     current
	DESCRIPTION "Gy credit-control terminate requests sent"

	::={ psmDiameterGyCreditcontrolTerminateRequestsSent 2 }

psmDiameterGyCreditcontrolTerminateRequestsSentMax OBJECT-TYPE
	SYNTAX     CounterBasedGauge64
	MAX-ACCESS read-only
	STATUS     current
	DESCRIPTION "Gy credit-control terminate requests sent"

	::={ psmDiameterGyCreditcontrolTerminateRequestsSent 3 }

psmDiameterGyCreditcontrolTerminateRequestsSentLevelTable OBJECT-TYPE
	SYNTAX     SEQUENCE OF PsmDiameterGyCreditcontrolTerminateRequestsSentLevelEntry
	MAX-ACCESS not-accessible
	STATUS     current
	DESCRIPTION
	"Gy credit-control terminate requests sent"
	::={ psmDiameterGyCreditcontrolTerminateRequestsSent 4 }

psmDiameterGyCreditcontrolTerminateRequestsSentLevelEntry OBJECT-TYPE
	SYNTAX      PsmDiameterGyCreditcontrolTerminateRequestsSentLevelEntry
	MAX-ACCESS  not-accessible
	STATUS      current
	DESCRIPTION
	"Gy credit-control terminate requests sent"
	INDEX { psmDiameterGyCreditcontrolTerminateRequestsSentLevelName }
	::={ psmDiameterGyCreditcontrolTerminateRequestsSentLevelTable 1 }

PsmDiameterGyCreditcontrolTerminateRequestsSentLevelEntry ::=
	SEQUENCE {
		psmDiameterGyCreditcontrolTerminateRequestsSentLevelName DisplayString,
		psmDiameterGyCreditcontrolTerminateRequestsSentLevelVal  Counter64,
		psmDiameterGyCreditcontrolTerminateRequestsSentLevelMom  CounterBasedGauge64,
		psmDiameterGyCreditcontrolTerminateRequestsSentLevelMax  CounterBasedGauge64
	}

psmDiameterGyCreditcontrolTerminateRequestsSentLevelName OBJECT-TYPE
	SYNTAX      DisplayString
	MAX-ACCESS  not-accessible
	STATUS      current
	DESCRIPTION
	"Gy credit-control terminate requests sent"
	::={ psmDiameterGyCreditcontrolTerminateRequestsSentLevelEntry 1}

psmDiameterGyCreditcontrolTerminateRequestsSentLevelVal OBJECT-TYPE
	SYNTAX     Counter64
	MAX-ACCESS read-only
	STATUS     current
	DESCRIPTION
	"Gy credit-control terminate requests sent"
	::={ psmDiameterGyCreditcontrolTerminateRequestsSentLevelEntry 2 }

psmDiameterGyCreditcontrolTerminateRequestsSentLevelMom OBJECT-TYPE
	SYNTAX     CounterBasedGauge64
	MAX-ACCESS read-only
	STATUS     current
	DESCRIPTION
	"Gy credit-control terminate requests sent"
	::={ psmDiameterGyCreditcontrolTerminateRequestsSentLevelEntry 3 }

psmDiameterGyCreditcontrolTerminateRequestsSentLevelMax OBJECT-TYPE
	SYNTAX     CounterBasedGauge64
	MAX-ACCESS read-only
	STATUS     current
	DESCRIPTION
	"Gy credit-control terminate requests sent"
	::={ psmDiameterGyCreditcontrolTerminateRequestsSentLevelEntry 4 }

psmDiameterGyCreditcontrolUpdateRequestsSent OBJECT IDENTIFIER ::= { psmDiameter 22 }

psmDiameterGyCreditcontrolUpdateRequestsSentVal OBJECT-TYPE
	SYNTAX     Counter64
	MAX-ACCESS read-only
	STATUS     current
	DESCRIPTION "Gy credit-control update requests sent"

	::={ psmDiameterGyCreditcontrolUpdateRequestsSent 1 }

psmDiameterGyCreditcontrolUpdateRequestsSentMom OBJECT-TYPE
	SYNTAX     CounterBasedGauge64
	MAX-ACCESS read-only
	STATUS     current
	DESCRIPTION "Gy credit-control update requests sent"

	::={ psmDiameterGyCreditcontrolUpdateRequestsSent 2 }

psmDiameterGyCreditcontrolUpdateRequestsSentMax OBJECT-TYPE
	SYNTAX     CounterBasedGauge64
	MAX-ACCESS read-only
	STATUS     current
	DESCRIPTION "Gy credit-control update requests sent"

	::={ psmDiameterGyCreditcontrolUpdateRequestsSent 3 }

psmDiameterGyCreditcontrolUpdateRequestsSentLevelTable OBJECT-TYPE
	SYNTAX     SEQUENCE OF PsmDiameterGyCreditcontrolUpdateRequestsSentLevelEntry
	MAX-ACCESS not-accessible
	STATUS     current
	DESCRIPTION
	"Gy credit-control update requests sent"
	::={ psmDiameterGyCreditcontrolUpdateRequestsSent 4 }

psmDiameterGyCreditcontrolUpdateRequestsSentLevelEntry OBJECT-TYPE
	SYNTAX      PsmDiameterGyCreditcontrolUpdateRequestsSentLevelEntry
	MAX-ACCESS  not-accessible
	STATUS      current
	DESCRIPTION
	"Gy credit-control update requests sent"
	INDEX { psmDiameterGyCreditcontrolUpdateRequestsSentLevelName }
	::={ psmDiameterGyCreditcontrolUpdateRequestsSentLevelTable 1 }

PsmDiameterGyCreditcontrolUpdateRequestsSentLevelEntry ::=
	SEQUENCE {
		psmDiameterGyCreditcontrolUpdateRequestsSentLevelName DisplayString,
		psmDiameterGyCreditcontrolUpdateRequestsSentLevelVal  Counter64,
		psmDiameterGyCreditcontrolUpdateRequestsSentLevelMom  CounterBasedGauge64,
		psmDiameterGyCreditcontrolUpdateRequestsSentLevelMax  CounterBasedGauge64
	}

psmDiameterGyCreditcontrolUpdateRequestsSentLevelName OBJECT-TYPE
	SYNTAX      DisplayString
	MAX-ACCESS  not-accessible
	STATUS      current
	DESCRIPTION
	"Gy credit-control update requests sent"
	::={ psmDiameterGyCreditcontrolUpdateRequestsSentLevelEntry 1}

psmDiameterGyCreditcontrolUpdateRequestsSentLevelVal OBJECT-TYPE
	SYNTAX     Counter64
	MAX-ACCESS read-only
	STATUS     current
	DESCRIPTION
	"Gy credit-control update requests sent"
	::={ psmDiameterGyCreditcontrolUpdateRequestsSentLevelEntry 2 }

psmDiameterGyCreditcontrolUpdateRequestsSentLevelMom OBJECT-TYPE
	SYNTAX     CounterBasedGauge64
	MAX-ACCESS read-only
	STATUS     current
	DESCRIPTION
	"Gy credit-control update requests sent"
	::={ psmDiameterGyCreditcontrolUpdateRequestsSentLevelEntry 3 }

psmDiameterGyCreditcontrolUpdateRequestsSentLevelMax OBJECT-TYPE
	SYNTAX     CounterBasedGauge64
	MAX-ACCESS read-only
	STATUS     current
	DESCRIPTION
	"Gy credit-control update requests sent"
	::={ psmDiameterGyCreditcontrolUpdateRequestsSentLevelEntry 4 }

psmDiameterGyReauthAnswersSent OBJECT IDENTIFIER ::= { psmDiameter 23 }

psmDiameterGyReauthAnswersSentVal OBJECT-TYPE
	SYNTAX     Counter64
	MAX-ACCESS read-only
	STATUS     current
	DESCRIPTION "Gy re-auth answers sent"

	::={ psmDiameterGyReauthAnswersSent 1 }

psmDiameterGyReauthAnswersSentMom OBJECT-TYPE
	SYNTAX     CounterBasedGauge64
	MAX-ACCESS read-only
	STATUS     current
	DESCRIPTION "Gy re-auth answers sent"

	::={ psmDiameterGyReauthAnswersSent 2 }

psmDiameterGyReauthAnswersSentMax OBJECT-TYPE
	SYNTAX     CounterBasedGauge64
	MAX-ACCESS read-only
	STATUS     current
	DESCRIPTION "Gy re-auth answers sent"

	::={ psmDiameterGyReauthAnswersSent 3 }

psmDiameterGyReauthAnswersSentLevelTable OBJECT-TYPE
	SYNTAX     SEQUENCE OF PsmDiameterGyReauthAnswersSentLevelEntry
	MAX-ACCESS not-accessible
	STATUS     current
	DESCRIPTION
	"Gy re-auth answers sent"
	::={ psmDiameterGyReauthAnswersSent 4 }

psmDiameterGyReauthAnswersSentLevelEntry OBJECT-TYPE
	SYNTAX      PsmDiameterGyReauthAnswersSentLevelEntry
	MAX-ACCESS  not-accessible
	STATUS      current
	DESCRIPTION
	"Gy re-auth answers sent"
	INDEX { psmDiameterGyReauthAnswersSentLevelName }
	::={ psmDiameterGyReauthAnswersSentLevelTable 1 }

PsmDiameterGyReauthAnswersSentLevelEntry ::=
	SEQUENCE {
		psmDiameterGyReauthAnswersSentLevelName DisplayString,
		psmDiameterGyReauthAnswersSentLevelVal  Counter64,
		psmDiameterGyReauthAnswersSentLevelMom  CounterBasedGauge64,
		psmDiameterGyReauthAnswersSentLevelMax  CounterBasedGauge64
	}

psmDiameterGyReauthAnswersSentLevelName OBJECT-TYPE
	SYNTAX      DisplayString
	MAX-ACCESS  not-accessible
	STATUS      current
	DESCRIPTION
	"Gy re-auth answers sent"
	::={ psmDiameterGyReauthAnswersSentLevelEntry 1}

psmDiameterGyReauthAnswersSentLevelVal OBJECT-TYPE
	SYNTAX     Counter64
	MAX-ACCESS read-only
	STATUS     current
	DESCRIPTION
	"Gy re-auth answers sent"
	::={ psmDiameterGyReauthAnswersSentLevelEntry 2 }

psmDiameterGyReauthAnswersSentLevelMom OBJECT-TYPE
	SYNTAX     CounterBasedGauge64
	MAX-ACCESS read-only
	STATUS     current
	DESCRIPTION
	"Gy re-auth answers sent"
	::={ psmDiameterGyReauthAnswersSentLevelEntry 3 }

psmDiameterGyReauthAnswersSentLevelMax OBJECT-TYPE
	SYNTAX     CounterBasedGauge64
	MAX-ACCESS read-only
	STATUS     current
	DESCRIPTION
	"Gy re-auth answers sent"
	::={ psmDiameterGyReauthAnswersSentLevelEntry 4 }

psmDiameterGyReauthRequestsReceived OBJECT IDENTIFIER ::= { psmDiameter 24 }

psmDiameterGyReauthRequestsReceivedVal OBJECT-TYPE
	SYNTAX     Counter64
	MAX-ACCESS read-only
	STATUS     current
	DESCRIPTION "Gy re-auth requests received"

	::={ psmDiameterGyReauthRequestsReceived 1 }

psmDiameterGyReauthRequestsReceivedMom OBJECT-TYPE
	SYNTAX     CounterBasedGauge64
	MAX-ACCESS read-only
	STATUS     current
	DESCRIPTION "Gy re-auth requests received"

	::={ psmDiameterGyReauthRequestsReceived 2 }

psmDiameterGyReauthRequestsReceivedMax OBJECT-TYPE
	SYNTAX     CounterBasedGauge64
	MAX-ACCESS read-only
	STATUS     current
	DESCRIPTION "Gy re-auth requests received"

	::={ psmDiameterGyReauthRequestsReceived 3 }

psmDiameterGyReauthRequestsReceivedLevelTable OBJECT-TYPE
	SYNTAX     SEQUENCE OF PsmDiameterGyReauthRequestsReceivedLevelEntry
	MAX-ACCESS not-accessible
	STATUS     current
	DESCRIPTION
	"Gy re-auth requests received"
	::={ psmDiameterGyReauthRequestsReceived 4 }

psmDiameterGyReauthRequestsReceivedLevelEntry OBJECT-TYPE
	SYNTAX      PsmDiameterGyReauthRequestsReceivedLevelEntry
	MAX-ACCESS  not-accessible
	STATUS      current
	DESCRIPTION
	"Gy re-auth requests received"
	INDEX { psmDiameterGyReauthRequestsReceivedLevelName }
	::={ psmDiameterGyReauthRequestsReceivedLevelTable 1 }

PsmDiameterGyReauthRequestsReceivedLevelEntry ::=
	SEQUENCE {
		psmDiameterGyReauthRequestsReceivedLevelName DisplayString,
		psmDiameterGyReauthRequestsReceivedLevelVal  Counter64,
		psmDiameterGyReauthRequestsReceivedLevelMom  CounterBasedGauge64,
		psmDiameterGyReauthRequestsReceivedLevelMax  CounterBasedGauge64
	}

psmDiameterGyReauthRequestsReceivedLevelName OBJECT-TYPE
	SYNTAX      DisplayString
	MAX-ACCESS  not-accessible
	STATUS      current
	DESCRIPTION
	"Gy re-auth requests received"
	::={ psmDiameterGyReauthRequestsReceivedLevelEntry 1}

psmDiameterGyReauthRequestsReceivedLevelVal OBJECT-TYPE
	SYNTAX     Counter64
	MAX-ACCESS read-only
	STATUS     current
	DESCRIPTION
	"Gy re-auth requests received"
	::={ psmDiameterGyReauthRequestsReceivedLevelEntry 2 }

psmDiameterGyReauthRequestsReceivedLevelMom OBJECT-TYPE
	SYNTAX     CounterBasedGauge64
	MAX-ACCESS read-only
	STATUS     current
	DESCRIPTION
	"Gy re-auth requests received"
	::={ psmDiameterGyReauthRequestsReceivedLevelEntry 3 }

psmDiameterGyReauthRequestsReceivedLevelMax OBJECT-TYPE
	SYNTAX     CounterBasedGauge64
	MAX-ACCESS read-only
	STATUS     current
	DESCRIPTION
	"Gy re-auth requests received"
	::={ psmDiameterGyReauthRequestsReceivedLevelEntry 4 }

psmDiameterLastConnectAttempt OBJECT IDENTIFIER ::= { psmDiameter 25 }

psmDiameterLastConnectAttemptVal OBJECT-TYPE
	SYNTAX     DateAndTime
	MAX-ACCESS read-only
	STATUS     current
	DESCRIPTION "Last connect attempt"

	::={ psmDiameterLastConnectAttempt 1 }

psmDiameterLastConnectAttemptLevelTable OBJECT-TYPE
	SYNTAX     SEQUENCE OF PsmDiameterLastConnectAttemptLevelEntry
	MAX-ACCESS not-accessible
	STATUS     current
	DESCRIPTION
	"Last connect attempt"
	::={ psmDiameterLastConnectAttempt 4 }

psmDiameterLastConnectAttemptLevelEntry OBJECT-TYPE
	SYNTAX      PsmDiameterLastConnectAttemptLevelEntry
	MAX-ACCESS  not-accessible
	STATUS      current
	DESCRIPTION
	"Last connect attempt"
	INDEX { psmDiameterLastConnectAttemptLevelName }
	::={ psmDiameterLastConnectAttemptLevelTable 1 }

PsmDiameterLastConnectAttemptLevelEntry ::=
	SEQUENCE {
		psmDiameterLastConnectAttemptLevelName DisplayString,
		psmDiameterLastConnectAttemptLevelVal  DateAndTime
	}

psmDiameterLastConnectAttemptLevelName OBJECT-TYPE
	SYNTAX      DisplayString
	MAX-ACCESS  not-accessible
	STATUS      current
	DESCRIPTION
	"Last connect attempt"
	::={ psmDiameterLastConnectAttemptLevelEntry 1}

psmDiameterLastConnectAttemptLevelVal OBJECT-TYPE
	SYNTAX     DateAndTime
	MAX-ACCESS read-only
	STATUS     current
	DESCRIPTION
	"Last connect attempt"
	::={ psmDiameterLastConnectAttemptLevelEntry 2 }

psmDiameterLastDisconnected OBJECT IDENTIFIER ::= { psmDiameter 26 }

psmDiameterLastDisconnectedVal OBJECT-TYPE
	SYNTAX     DateAndTime
	MAX-ACCESS read-only
	STATUS     current
	DESCRIPTION "Last disconnected"

	::={ psmDiameterLastDisconnected 1 }

psmDiameterLastDisconnectedLevelTable OBJECT-TYPE
	SYNTAX     SEQUENCE OF PsmDiameterLastDisconnectedLevelEntry
	MAX-ACCESS not-accessible
	STATUS     current
	DESCRIPTION
	"Last disconnected"
	::={ psmDiameterLastDisconnected 4 }

psmDiameterLastDisconnectedLevelEntry OBJECT-TYPE
	SYNTAX      PsmDiameterLastDisconnectedLevelEntry
	MAX-ACCESS  not-accessible
	STATUS      current
	DESCRIPTION
	"Last disconnected"
	INDEX { psmDiameterLastDisconnectedLevelName }
	::={ psmDiameterLastDisconnectedLevelTable 1 }

PsmDiameterLastDisconnectedLevelEntry ::=
	SEQUENCE {
		psmDiameterLastDisconnectedLevelName DisplayString,
		psmDiameterLastDisconnectedLevelVal  DateAndTime
	}

psmDiameterLastDisconnectedLevelName OBJECT-TYPE
	SYNTAX      DisplayString
	MAX-ACCESS  not-accessible
	STATUS      current
	DESCRIPTION
	"Last disconnected"
	::={ psmDiameterLastDisconnectedLevelEntry 1}

psmDiameterLastDisconnectedLevelVal OBJECT-TYPE
	SYNTAX     DateAndTime
	MAX-ACCESS read-only
	STATUS     current
	DESCRIPTION
	"Last disconnected"
	::={ psmDiameterLastDisconnectedLevelEntry 2 }

psmDiameterLastNegotiationAttempt OBJECT IDENTIFIER ::= { psmDiameter 27 }

psmDiameterLastNegotiationAttemptVal OBJECT-TYPE
	SYNTAX     DateAndTime
	MAX-ACCESS read-only
	STATUS     current
	DESCRIPTION "Last negotiation attempt"

	::={ psmDiameterLastNegotiationAttempt 1 }

psmDiameterLastNegotiationAttemptLevelTable OBJECT-TYPE
	SYNTAX     SEQUENCE OF PsmDiameterLastNegotiationAttemptLevelEntry
	MAX-ACCESS not-accessible
	STATUS     current
	DESCRIPTION
	"Last negotiation attempt"
	::={ psmDiameterLastNegotiationAttempt 4 }

psmDiameterLastNegotiationAttemptLevelEntry OBJECT-TYPE
	SYNTAX      PsmDiameterLastNegotiationAttemptLevelEntry
	MAX-ACCESS  not-accessible
	STATUS      current
	DESCRIPTION
	"Last negotiation attempt"
	INDEX { psmDiameterLastNegotiationAttemptLevelName }
	::={ psmDiameterLastNegotiationAttemptLevelTable 1 }

PsmDiameterLastNegotiationAttemptLevelEntry ::=
	SEQUENCE {
		psmDiameterLastNegotiationAttemptLevelName DisplayString,
		psmDiameterLastNegotiationAttemptLevelVal  DateAndTime
	}

psmDiameterLastNegotiationAttemptLevelName OBJECT-TYPE
	SYNTAX      DisplayString
	MAX-ACCESS  not-accessible
	STATUS      current
	DESCRIPTION
	"Last negotiation attempt"
	::={ psmDiameterLastNegotiationAttemptLevelEntry 1}

psmDiameterLastNegotiationAttemptLevelVal OBJECT-TYPE
	SYNTAX     DateAndTime
	MAX-ACCESS read-only
	STATUS     current
	DESCRIPTION
	"Last negotiation attempt"
	::={ psmDiameterLastNegotiationAttemptLevelEntry 2 }

psmDiameterLastOnline OBJECT IDENTIFIER ::= { psmDiameter 28 }

psmDiameterLastOnlineVal OBJECT-TYPE
	SYNTAX     DateAndTime
	MAX-ACCESS read-only
	STATUS     current
	DESCRIPTION "Last online"

	::={ psmDiameterLastOnline 1 }

psmDiameterLastOnlineLevelTable OBJECT-TYPE
	SYNTAX     SEQUENCE OF PsmDiameterLastOnlineLevelEntry
	MAX-ACCESS not-accessible
	STATUS     current
	DESCRIPTION
	"Last online"
	::={ psmDiameterLastOnline 4 }

psmDiameterLastOnlineLevelEntry OBJECT-TYPE
	SYNTAX      PsmDiameterLastOnlineLevelEntry
	MAX-ACCESS  not-accessible
	STATUS      current
	DESCRIPTION
	"Last online"
	INDEX { psmDiameterLastOnlineLevelName }
	::={ psmDiameterLastOnlineLevelTable 1 }

PsmDiameterLastOnlineLevelEntry ::=
	SEQUENCE {
		psmDiameterLastOnlineLevelName DisplayString,
		psmDiameterLastOnlineLevelVal  DateAndTime
	}

psmDiameterLastOnlineLevelName OBJECT-TYPE
	SYNTAX      DisplayString
	MAX-ACCESS  not-accessible
	STATUS      current
	DESCRIPTION
	"Last online"
	::={ psmDiameterLastOnlineLevelEntry 1}

psmDiameterLastOnlineLevelVal OBJECT-TYPE
	SYNTAX     DateAndTime
	MAX-ACCESS read-only
	STATUS     current
	DESCRIPTION
	"Last online"
	::={ psmDiameterLastOnlineLevelEntry 2 }

psmDiameterReceivedMessages OBJECT IDENTIFIER ::= { psmDiameter 29 }

psmDiameterReceivedMessagesVal OBJECT-TYPE
	SYNTAX     Counter64
	MAX-ACCESS read-only
	STATUS     current
	DESCRIPTION "Received messages"

	::={ psmDiameterReceivedMessages 1 }

psmDiameterReceivedMessagesMom OBJECT-TYPE
	SYNTAX     CounterBasedGauge64
	MAX-ACCESS read-only
	STATUS     current
	DESCRIPTION "Received messages"

	::={ psmDiameterReceivedMessages 2 }

psmDiameterReceivedMessagesMax OBJECT-TYPE
	SYNTAX     CounterBasedGauge64
	MAX-ACCESS read-only
	STATUS     current
	DESCRIPTION "Received messages"

	::={ psmDiameterReceivedMessages 3 }

psmDiameterReceivedMessagesLevelTable OBJECT-TYPE
	SYNTAX     SEQUENCE OF PsmDiameterReceivedMessagesLevelEntry
	MAX-ACCESS not-accessible
	STATUS     current
	DESCRIPTION
	"Received messages"
	::={ psmDiameterReceivedMessages 4 }

psmDiameterReceivedMessagesLevelEntry OBJECT-TYPE
	SYNTAX      PsmDiameterReceivedMessagesLevelEntry
	MAX-ACCESS  not-accessible
	STATUS      current
	DESCRIPTION
	"Received messages"
	INDEX { psmDiameterReceivedMessagesLevelName }
	::={ psmDiameterReceivedMessagesLevelTable 1 }

PsmDiameterReceivedMessagesLevelEntry ::=
	SEQUENCE {
		psmDiameterReceivedMessagesLevelName DisplayString,
		psmDiameterReceivedMessagesLevelVal  Counter64,
		psmDiameterReceivedMessagesLevelMom  CounterBasedGauge64,
		psmDiameterReceivedMessagesLevelMax  CounterBasedGauge64
	}

psmDiameterReceivedMessagesLevelName OBJECT-TYPE
	SYNTAX      DisplayString
	MAX-ACCESS  not-accessible
	STATUS      current
	DESCRIPTION
	"Received messages"
	::={ psmDiameterReceivedMessagesLevelEntry 1}

psmDiameterReceivedMessagesLevelVal OBJECT-TYPE
	SYNTAX     Counter64
	MAX-ACCESS read-only
	STATUS     current
	DESCRIPTION
	"Received messages"
	::={ psmDiameterReceivedMessagesLevelEntry 2 }

psmDiameterReceivedMessagesLevelMom OBJECT-TYPE
	SYNTAX     CounterBasedGauge64
	MAX-ACCESS read-only
	STATUS     current
	DESCRIPTION
	"Received messages"
	::={ psmDiameterReceivedMessagesLevelEntry 3 }

psmDiameterReceivedMessagesLevelMax OBJECT-TYPE
	SYNTAX     CounterBasedGauge64
	MAX-ACCESS read-only
	STATUS     current
	DESCRIPTION
	"Received messages"
	::={ psmDiameterReceivedMessagesLevelEntry 4 }

psmDiameterSentMessages OBJECT IDENTIFIER ::= { psmDiameter 30 }

psmDiameterSentMessagesVal OBJECT-TYPE
	SYNTAX     Counter64
	MAX-ACCESS read-only
	STATUS     current
	DESCRIPTION "Sent messages"

	::={ psmDiameterSentMessages 1 }

psmDiameterSentMessagesMom OBJECT-TYPE
	SYNTAX     CounterBasedGauge64
	MAX-ACCESS read-only
	STATUS     current
	DESCRIPTION "Sent messages"

	::={ psmDiameterSentMessages 2 }

psmDiameterSentMessagesMax OBJECT-TYPE
	SYNTAX     CounterBasedGauge64
	MAX-ACCESS read-only
	STATUS     current
	DESCRIPTION "Sent messages"

	::={ psmDiameterSentMessages 3 }

psmDiameterSentMessagesLevelTable OBJECT-TYPE
	SYNTAX     SEQUENCE OF PsmDiameterSentMessagesLevelEntry
	MAX-ACCESS not-accessible
	STATUS     current
	DESCRIPTION
	"Sent messages"
	::={ psmDiameterSentMessages 4 }

psmDiameterSentMessagesLevelEntry OBJECT-TYPE
	SYNTAX      PsmDiameterSentMessagesLevelEntry
	MAX-ACCESS  not-accessible
	STATUS      current
	DESCRIPTION
	"Sent messages"
	INDEX { psmDiameterSentMessagesLevelName }
	::={ psmDiameterSentMessagesLevelTable 1 }

PsmDiameterSentMessagesLevelEntry ::=
	SEQUENCE {
		psmDiameterSentMessagesLevelName DisplayString,
		psmDiameterSentMessagesLevelVal  Counter64,
		psmDiameterSentMessagesLevelMom  CounterBasedGauge64,
		psmDiameterSentMessagesLevelMax  CounterBasedGauge64
	}

psmDiameterSentMessagesLevelName OBJECT-TYPE
	SYNTAX      DisplayString
	MAX-ACCESS  not-accessible
	STATUS      current
	DESCRIPTION
	"Sent messages"
	::={ psmDiameterSentMessagesLevelEntry 1}

psmDiameterSentMessagesLevelVal OBJECT-TYPE
	SYNTAX     Counter64
	MAX-ACCESS read-only
	STATUS     current
	DESCRIPTION
	"Sent messages"
	::={ psmDiameterSentMessagesLevelEntry 2 }

psmDiameterSentMessagesLevelMom OBJECT-TYPE
	SYNTAX     CounterBasedGauge64
	MAX-ACCESS read-only
	STATUS     current
	DESCRIPTION
	"Sent messages"
	::={ psmDiameterSentMessagesLevelEntry 3 }

psmDiameterSentMessagesLevelMax OBJECT-TYPE
	SYNTAX     CounterBasedGauge64
	MAX-ACCESS read-only
	STATUS     current
	DESCRIPTION
	"Sent messages"
	::={ psmDiameterSentMessagesLevelEntry 4 }

psmDiameterReconnects OBJECT IDENTIFIER ::= { psmDiameter 31 }

psmDiameterReconnectsVal OBJECT-TYPE
	SYNTAX     Counter64
	MAX-ACCESS read-only
	STATUS     current
	DESCRIPTION "Reconnects"

	::={ psmDiameterReconnects 1 }

psmDiameterReconnectsMom OBJECT-TYPE
	SYNTAX     CounterBasedGauge64
	MAX-ACCESS read-only
	STATUS     current
	DESCRIPTION "Reconnects"

	::={ psmDiameterReconnects 2 }

psmDiameterReconnectsMax OBJECT-TYPE
	SYNTAX     CounterBasedGauge64
	MAX-ACCESS read-only
	STATUS     current
	DESCRIPTION "Reconnects"

	::={ psmDiameterReconnects 3 }

psmDiameterReconnectsLevelTable OBJECT-TYPE
	SYNTAX     SEQUENCE OF PsmDiameterReconnectsLevelEntry
	MAX-ACCESS not-accessible
	STATUS     current
	DESCRIPTION
	"Reconnects"
	::={ psmDiameterReconnects 4 }

psmDiameterReconnectsLevelEntry OBJECT-TYPE
	SYNTAX      PsmDiameterReconnectsLevelEntry
	MAX-ACCESS  not-accessible
	STATUS      current
	DESCRIPTION
	"Reconnects"
	INDEX { psmDiameterReconnectsLevelName }
	::={ psmDiameterReconnectsLevelTable 1 }

PsmDiameterReconnectsLevelEntry ::=
	SEQUENCE {
		psmDiameterReconnectsLevelName DisplayString,
		psmDiameterReconnectsLevelVal  Counter64,
		psmDiameterReconnectsLevelMom  CounterBasedGauge64,
		psmDiameterReconnectsLevelMax  CounterBasedGauge64
	}

psmDiameterReconnectsLevelName OBJECT-TYPE
	SYNTAX      DisplayString
	MAX-ACCESS  not-accessible
	STATUS      current
	DESCRIPTION
	"Reconnects"
	::={ psmDiameterReconnectsLevelEntry 1}

psmDiameterReconnectsLevelVal OBJECT-TYPE
	SYNTAX     Counter64
	MAX-ACCESS read-only
	STATUS     current
	DESCRIPTION
	"Reconnects"
	::={ psmDiameterReconnectsLevelEntry 2 }

psmDiameterReconnectsLevelMom OBJECT-TYPE
	SYNTAX     CounterBasedGauge64
	MAX-ACCESS read-only
	STATUS     current
	DESCRIPTION
	"Reconnects"
	::={ psmDiameterReconnectsLevelEntry 3 }

psmDiameterReconnectsLevelMax OBJECT-TYPE
	SYNTAX     CounterBasedGauge64
	MAX-ACCESS read-only
	STATUS     current
	DESCRIPTION
	"Reconnects"
	::={ psmDiameterReconnectsLevelEntry 4 }

psmDiameterRequestRoundTripTimeLess1ms OBJECT IDENTIFIER ::= { psmDiameter 32 }

psmDiameterRequestRoundTripTimeLess1msVal OBJECT-TYPE
	SYNTAX     Counter64
	MAX-ACCESS read-only
	STATUS     current
	DESCRIPTION "Request round trip time <= 1000ms"

	::={ psmDiameterRequestRoundTripTimeLess1ms 1 }

psmDiameterRequestRoundTripTimeLess1msMom OBJECT-TYPE
	SYNTAX     CounterBasedGauge64
	MAX-ACCESS read-only
	STATUS     current
	DESCRIPTION "Request round trip time <= 1000ms"

	::={ psmDiameterRequestRoundTripTimeLess1ms 2 }

psmDiameterRequestRoundTripTimeLess1msMax OBJECT-TYPE
	SYNTAX     CounterBasedGauge64
	MAX-ACCESS read-only
	STATUS     current
	DESCRIPTION "Request round trip time <= 1000ms"

	::={ psmDiameterRequestRoundTripTimeLess1ms 3 }

psmDiameterRequestRoundTripTimeLess1msLevelTable OBJECT-TYPE
	SYNTAX     SEQUENCE OF PsmDiameterRequestRoundTripTimeLess1msLevelEntry
	MAX-ACCESS not-accessible
	STATUS     current
	DESCRIPTION
	"Request round trip time <= 1000ms"
	::={ psmDiameterRequestRoundTripTimeLess1ms 4 }

psmDiameterRequestRoundTripTimeLess1msLevelEntry OBJECT-TYPE
	SYNTAX      PsmDiameterRequestRoundTripTimeLess1msLevelEntry
	MAX-ACCESS  not-accessible
	STATUS      current
	DESCRIPTION
	"Request round trip time <= 1000ms"
	INDEX { psmDiameterRequestRoundTripTimeLess1msLevelName }
	::={ psmDiameterRequestRoundTripTimeLess1msLevelTable 1 }

PsmDiameterRequestRoundTripTimeLess1msLevelEntry ::=
	SEQUENCE {
		psmDiameterRequestRoundTripTimeLess1msLevelName DisplayString,
		psmDiameterRequestRoundTripTimeLess1msLevelVal  Counter64,
		psmDiameterRequestRoundTripTimeLess1msLevelMom  CounterBasedGauge64,
		psmDiameterRequestRoundTripTimeLess1msLevelMax  CounterBasedGauge64
	}

psmDiameterRequestRoundTripTimeLess1msLevelName OBJECT-TYPE
	SYNTAX      DisplayString
	MAX-ACCESS  not-accessible
	STATUS      current
	DESCRIPTION
	"Request round trip time <= 1000ms"
	::={ psmDiameterRequestRoundTripTimeLess1msLevelEntry 1}

psmDiameterRequestRoundTripTimeLess1msLevelVal OBJECT-TYPE
	SYNTAX     Counter64
	MAX-ACCESS read-only
	STATUS     current
	DESCRIPTION
	"Request round trip time <= 1000ms"
	::={ psmDiameterRequestRoundTripTimeLess1msLevelEntry 2 }

psmDiameterRequestRoundTripTimeLess1msLevelMom OBJECT-TYPE
	SYNTAX     CounterBasedGauge64
	MAX-ACCESS read-only
	STATUS     current
	DESCRIPTION
	"Request round trip time <= 1000ms"
	::={ psmDiameterRequestRoundTripTimeLess1msLevelEntry 3 }

psmDiameterRequestRoundTripTimeLess1msLevelMax OBJECT-TYPE
	SYNTAX     CounterBasedGauge64
	MAX-ACCESS read-only
	STATUS     current
	DESCRIPTION
	"Request round trip time <= 1000ms"
	::={ psmDiameterRequestRoundTripTimeLess1msLevelEntry 4 }

psmDiameterRequestRoundTripTimeLess1ms OBJECT IDENTIFIER ::= { psmDiameter 33 }

psmDiameterRequestRoundTripTimeLess1msVal OBJECT-TYPE
	SYNTAX     Counter64
	MAX-ACCESS read-only
	STATUS     current
	DESCRIPTION "Request round trip time <= 100ms"

	::={ psmDiameterRequestRoundTripTimeLess1ms 1 }

psmDiameterRequestRoundTripTimeLess1msMom OBJECT-TYPE
	SYNTAX     CounterBasedGauge64
	MAX-ACCESS read-only
	STATUS     current
	DESCRIPTION "Request round trip time <= 100ms"

	::={ psmDiameterRequestRoundTripTimeLess1ms 2 }

psmDiameterRequestRoundTripTimeLess1msMax OBJECT-TYPE
	SYNTAX     CounterBasedGauge64
	MAX-ACCESS read-only
	STATUS     current
	DESCRIPTION "Request round trip time <= 100ms"

	::={ psmDiameterRequestRoundTripTimeLess1ms 3 }

psmDiameterRequestRoundTripTimeLess1msLevelTable OBJECT-TYPE
	SYNTAX     SEQUENCE OF PsmDiameterRequestRoundTripTimeLess1msLevelEntry
	MAX-ACCESS not-accessible
	STATUS     current
	DESCRIPTION
	"Request round trip time <= 100ms"
	::={ psmDiameterRequestRoundTripTimeLess1ms 4 }

psmDiameterRequestRoundTripTimeLess1msLevelEntry OBJECT-TYPE
	SYNTAX      PsmDiameterRequestRoundTripTimeLess1msLevelEntry
	MAX-ACCESS  not-accessible
	STATUS      current
	DESCRIPTION
	"Request round trip time <= 100ms"
	INDEX { psmDiameterRequestRoundTripTimeLess1msLevelName }
	::={ psmDiameterRequestRoundTripTimeLess1msLevelTable 1 }

PsmDiameterRequestRoundTripTimeLess1msLevelEntry ::=
	SEQUENCE {
		psmDiameterRequestRoundTripTimeLess1msLevelName DisplayString,
		psmDiameterRequestRoundTripTimeLess1msLevelVal  Counter64,
		psmDiameterRequestRoundTripTimeLess1msLevelMom  CounterBasedGauge64,
		psmDiameterRequestRoundTripTimeLess1msLevelMax  CounterBasedGauge64
	}

psmDiameterRequestRoundTripTimeLess1msLevelName OBJECT-TYPE
	SYNTAX      DisplayString
	MAX-ACCESS  not-accessible
	STATUS      current
	DESCRIPTION
	"Request round trip time <= 100ms"
	::={ psmDiameterRequestRoundTripTimeLess1msLevelEntry 1}

psmDiameterRequestRoundTripTimeLess1msLevelVal OBJECT-TYPE
	SYNTAX     Counter64
	MAX-ACCESS read-only
	STATUS     current
	DESCRIPTION
	"Request round trip time <= 100ms"
	::={ psmDiameterRequestRoundTripTimeLess1msLevelEntry 2 }

psmDiameterRequestRoundTripTimeLess1msLevelMom OBJECT-TYPE
	SYNTAX     CounterBasedGauge64
	MAX-ACCESS read-only
	STATUS     current
	DESCRIPTION
	"Request round trip time <= 100ms"
	::={ psmDiameterRequestRoundTripTimeLess1msLevelEntry 3 }

psmDiameterRequestRoundTripTimeLess1msLevelMax OBJECT-TYPE
	SYNTAX     CounterBasedGauge64
	MAX-ACCESS read-only
	STATUS     current
	DESCRIPTION
	"Request round trip time <= 100ms"
	::={ psmDiameterRequestRoundTripTimeLess1msLevelEntry 4 }

psmDiameterRequestRoundTripTimeLess2ms OBJECT IDENTIFIER ::= { psmDiameter 34 }

psmDiameterRequestRoundTripTimeLess2msVal OBJECT-TYPE
	SYNTAX     Counter64
	MAX-ACCESS read-only
	STATUS     current
	DESCRIPTION "Request round trip time <= 2000ms"

	::={ psmDiameterRequestRoundTripTimeLess2ms 1 }

psmDiameterRequestRoundTripTimeLess2msMom OBJECT-TYPE
	SYNTAX     CounterBasedGauge64
	MAX-ACCESS read-only
	STATUS     current
	DESCRIPTION "Request round trip time <= 2000ms"

	::={ psmDiameterRequestRoundTripTimeLess2ms 2 }

psmDiameterRequestRoundTripTimeLess2msMax OBJECT-TYPE
	SYNTAX     CounterBasedGauge64
	MAX-ACCESS read-only
	STATUS     current
	DESCRIPTION "Request round trip time <= 2000ms"

	::={ psmDiameterRequestRoundTripTimeLess2ms 3 }

psmDiameterRequestRoundTripTimeLess2msLevelTable OBJECT-TYPE
	SYNTAX     SEQUENCE OF PsmDiameterRequestRoundTripTimeLess2msLevelEntry
	MAX-ACCESS not-accessible
	STATUS     current
	DESCRIPTION
	"Request round trip time <= 2000ms"
	::={ psmDiameterRequestRoundTripTimeLess2ms 4 }

psmDiameterRequestRoundTripTimeLess2msLevelEntry OBJECT-TYPE
	SYNTAX      PsmDiameterRequestRoundTripTimeLess2msLevelEntry
	MAX-ACCESS  not-accessible
	STATUS      current
	DESCRIPTION
	"Request round trip time <= 2000ms"
	INDEX { psmDiameterRequestRoundTripTimeLess2msLevelName }
	::={ psmDiameterRequestRoundTripTimeLess2msLevelTable 1 }

PsmDiameterRequestRoundTripTimeLess2msLevelEntry ::=
	SEQUENCE {
		psmDiameterRequestRoundTripTimeLess2msLevelName DisplayString,
		psmDiameterRequestRoundTripTimeLess2msLevelVal  Counter64,
		psmDiameterRequestRoundTripTimeLess2msLevelMom  CounterBasedGauge64,
		psmDiameterRequestRoundTripTimeLess2msLevelMax  CounterBasedGauge64
	}

psmDiameterRequestRoundTripTimeLess2msLevelName OBJECT-TYPE
	SYNTAX      DisplayString
	MAX-ACCESS  not-accessible
	STATUS      current
	DESCRIPTION
	"Request round trip time <= 2000ms"
	::={ psmDiameterRequestRoundTripTimeLess2msLevelEntry 1}

psmDiameterRequestRoundTripTimeLess2msLevelVal OBJECT-TYPE
	SYNTAX     Counter64
	MAX-ACCESS read-only
	STATUS     current
	DESCRIPTION
	"Request round trip time <= 2000ms"
	::={ psmDiameterRequestRoundTripTimeLess2msLevelEntry 2 }

psmDiameterRequestRoundTripTimeLess2msLevelMom OBJECT-TYPE
	SYNTAX     CounterBasedGauge64
	MAX-ACCESS read-only
	STATUS     current
	DESCRIPTION
	"Request round trip time <= 2000ms"
	::={ psmDiameterRequestRoundTripTimeLess2msLevelEntry 3 }

psmDiameterRequestRoundTripTimeLess2msLevelMax OBJECT-TYPE
	SYNTAX     CounterBasedGauge64
	MAX-ACCESS read-only
	STATUS     current
	DESCRIPTION
	"Request round trip time <= 2000ms"
	::={ psmDiameterRequestRoundTripTimeLess2msLevelEntry 4 }

psmDiameterRequestRoundTripTimeLess2ms OBJECT IDENTIFIER ::= { psmDiameter 35 }

psmDiameterRequestRoundTripTimeLess2msVal OBJECT-TYPE
	SYNTAX     Counter64
	MAX-ACCESS read-only
	STATUS     current
	DESCRIPTION "Request round trip time <= 200ms"

	::={ psmDiameterRequestRoundTripTimeLess2ms 1 }

psmDiameterRequestRoundTripTimeLess2msMom OBJECT-TYPE
	SYNTAX     CounterBasedGauge64
	MAX-ACCESS read-only
	STATUS     current
	DESCRIPTION "Request round trip time <= 200ms"

	::={ psmDiameterRequestRoundTripTimeLess2ms 2 }

psmDiameterRequestRoundTripTimeLess2msMax OBJECT-TYPE
	SYNTAX     CounterBasedGauge64
	MAX-ACCESS read-only
	STATUS     current
	DESCRIPTION "Request round trip time <= 200ms"

	::={ psmDiameterRequestRoundTripTimeLess2ms 3 }

psmDiameterRequestRoundTripTimeLess2msLevelTable OBJECT-TYPE
	SYNTAX     SEQUENCE OF PsmDiameterRequestRoundTripTimeLess2msLevelEntry
	MAX-ACCESS not-accessible
	STATUS     current
	DESCRIPTION
	"Request round trip time <= 200ms"
	::={ psmDiameterRequestRoundTripTimeLess2ms 4 }

psmDiameterRequestRoundTripTimeLess2msLevelEntry OBJECT-TYPE
	SYNTAX      PsmDiameterRequestRoundTripTimeLess2msLevelEntry
	MAX-ACCESS  not-accessible
	STATUS      current
	DESCRIPTION
	"Request round trip time <= 200ms"
	INDEX { psmDiameterRequestRoundTripTimeLess2msLevelName }
	::={ psmDiameterRequestRoundTripTimeLess2msLevelTable 1 }

PsmDiameterRequestRoundTripTimeLess2msLevelEntry ::=
	SEQUENCE {
		psmDiameterRequestRoundTripTimeLess2msLevelName DisplayString,
		psmDiameterRequestRoundTripTimeLess2msLevelVal  Counter64,
		psmDiameterRequestRoundTripTimeLess2msLevelMom  CounterBasedGauge64,
		psmDiameterRequestRoundTripTimeLess2msLevelMax  CounterBasedGauge64
	}

psmDiameterRequestRoundTripTimeLess2msLevelName OBJECT-TYPE
	SYNTAX      DisplayString
	MAX-ACCESS  not-accessible
	STATUS      current
	DESCRIPTION
	"Request round trip time <= 200ms"
	::={ psmDiameterRequestRoundTripTimeLess2msLevelEntry 1}

psmDiameterRequestRoundTripTimeLess2msLevelVal OBJECT-TYPE
	SYNTAX     Counter64
	MAX-ACCESS read-only
	STATUS     current
	DESCRIPTION
	"Request round trip time <= 200ms"
	::={ psmDiameterRequestRoundTripTimeLess2msLevelEntry 2 }

psmDiameterRequestRoundTripTimeLess2msLevelMom OBJECT-TYPE
	SYNTAX     CounterBasedGauge64
	MAX-ACCESS read-only
	STATUS     current
	DESCRIPTION
	"Request round trip time <= 200ms"
	::={ psmDiameterRequestRoundTripTimeLess2msLevelEntry 3 }

psmDiameterRequestRoundTripTimeLess2msLevelMax OBJECT-TYPE
	SYNTAX     CounterBasedGauge64
	MAX-ACCESS read-only
	STATUS     current
	DESCRIPTION
	"Request round trip time <= 200ms"
	::={ psmDiameterRequestRoundTripTimeLess2msLevelEntry 4 }

psmDiameterRequestRoundTripTimeLess5ms OBJECT IDENTIFIER ::= { psmDiameter 36 }

psmDiameterRequestRoundTripTimeLess5msVal OBJECT-TYPE
	SYNTAX     Counter64
	MAX-ACCESS read-only
	STATUS     current
	DESCRIPTION "Request round trip time <= 5000ms"

	::={ psmDiameterRequestRoundTripTimeLess5ms 1 }

psmDiameterRequestRoundTripTimeLess5msMom OBJECT-TYPE
	SYNTAX     CounterBasedGauge64
	MAX-ACCESS read-only
	STATUS     current
	DESCRIPTION "Request round trip time <= 5000ms"

	::={ psmDiameterRequestRoundTripTimeLess5ms 2 }

psmDiameterRequestRoundTripTimeLess5msMax OBJECT-TYPE
	SYNTAX     CounterBasedGauge64
	MAX-ACCESS read-only
	STATUS     current
	DESCRIPTION "Request round trip time <= 5000ms"

	::={ psmDiameterRequestRoundTripTimeLess5ms 3 }

psmDiameterRequestRoundTripTimeLess5msLevelTable OBJECT-TYPE
	SYNTAX     SEQUENCE OF PsmDiameterRequestRoundTripTimeLess5msLevelEntry
	MAX-ACCESS not-accessible
	STATUS     current
	DESCRIPTION
	"Request round trip time <= 5000ms"
	::={ psmDiameterRequestRoundTripTimeLess5ms 4 }

psmDiameterRequestRoundTripTimeLess5msLevelEntry OBJECT-TYPE
	SYNTAX      PsmDiameterRequestRoundTripTimeLess5msLevelEntry
	MAX-ACCESS  not-accessible
	STATUS      current
	DESCRIPTION
	"Request round trip time <= 5000ms"
	INDEX { psmDiameterRequestRoundTripTimeLess5msLevelName }
	::={ psmDiameterRequestRoundTripTimeLess5msLevelTable 1 }

PsmDiameterRequestRoundTripTimeLess5msLevelEntry ::=
	SEQUENCE {
		psmDiameterRequestRoundTripTimeLess5msLevelName DisplayString,
		psmDiameterRequestRoundTripTimeLess5msLevelVal  Counter64,
		psmDiameterRequestRoundTripTimeLess5msLevelMom  CounterBasedGauge64,
		psmDiameterRequestRoundTripTimeLess5msLevelMax  CounterBasedGauge64
	}

psmDiameterRequestRoundTripTimeLess5msLevelName OBJECT-TYPE
	SYNTAX      DisplayString
	MAX-ACCESS  not-accessible
	STATUS      current
	DESCRIPTION
	"Request round trip time <= 5000ms"
	::={ psmDiameterRequestRoundTripTimeLess5msLevelEntry 1}

psmDiameterRequestRoundTripTimeLess5msLevelVal OBJECT-TYPE
	SYNTAX     Counter64
	MAX-ACCESS read-only
	STATUS     current
	DESCRIPTION
	"Request round trip time <= 5000ms"
	::={ psmDiameterRequestRoundTripTimeLess5msLevelEntry 2 }

psmDiameterRequestRoundTripTimeLess5msLevelMom OBJECT-TYPE
	SYNTAX     CounterBasedGauge64
	MAX-ACCESS read-only
	STATUS     current
	DESCRIPTION
	"Request round trip time <= 5000ms"
	::={ psmDiameterRequestRoundTripTimeLess5msLevelEntry 3 }

psmDiameterRequestRoundTripTimeLess5msLevelMax OBJECT-TYPE
	SYNTAX     CounterBasedGauge64
	MAX-ACCESS read-only
	STATUS     current
	DESCRIPTION
	"Request round trip time <= 5000ms"
	::={ psmDiameterRequestRoundTripTimeLess5msLevelEntry 4 }

psmDiameterRequestRoundTripTimeMore5ms OBJECT IDENTIFIER ::= { psmDiameter 37 }

psmDiameterRequestRoundTripTimeMore5msVal OBJECT-TYPE
	SYNTAX     Counter64
	MAX-ACCESS read-only
	STATUS     current
	DESCRIPTION "Request round trip time > 5000ms"

	::={ psmDiameterRequestRoundTripTimeMore5ms 1 }

psmDiameterRequestRoundTripTimeMore5msMom OBJECT-TYPE
	SYNTAX     CounterBasedGauge64
	MAX-ACCESS read-only
	STATUS     current
	DESCRIPTION "Request round trip time > 5000ms"

	::={ psmDiameterRequestRoundTripTimeMore5ms 2 }

psmDiameterRequestRoundTripTimeMore5msMax OBJECT-TYPE
	SYNTAX     CounterBasedGauge64
	MAX-ACCESS read-only
	STATUS     current
	DESCRIPTION "Request round trip time > 5000ms"

	::={ psmDiameterRequestRoundTripTimeMore5ms 3 }

psmDiameterRequestRoundTripTimeMore5msLevelTable OBJECT-TYPE
	SYNTAX     SEQUENCE OF PsmDiameterRequestRoundTripTimeMore5msLevelEntry
	MAX-ACCESS not-accessible
	STATUS     current
	DESCRIPTION
	"Request round trip time > 5000ms"
	::={ psmDiameterRequestRoundTripTimeMore5ms 4 }

psmDiameterRequestRoundTripTimeMore5msLevelEntry OBJECT-TYPE
	SYNTAX      PsmDiameterRequestRoundTripTimeMore5msLevelEntry
	MAX-ACCESS  not-accessible
	STATUS      current
	DESCRIPTION
	"Request round trip time > 5000ms"
	INDEX { psmDiameterRequestRoundTripTimeMore5msLevelName }
	::={ psmDiameterRequestRoundTripTimeMore5msLevelTable 1 }

PsmDiameterRequestRoundTripTimeMore5msLevelEntry ::=
	SEQUENCE {
		psmDiameterRequestRoundTripTimeMore5msLevelName DisplayString,
		psmDiameterRequestRoundTripTimeMore5msLevelVal  Counter64,
		psmDiameterRequestRoundTripTimeMore5msLevelMom  CounterBasedGauge64,
		psmDiameterRequestRoundTripTimeMore5msLevelMax  CounterBasedGauge64
	}

psmDiameterRequestRoundTripTimeMore5msLevelName OBJECT-TYPE
	SYNTAX      DisplayString
	MAX-ACCESS  not-accessible
	STATUS      current
	DESCRIPTION
	"Request round trip time > 5000ms"
	::={ psmDiameterRequestRoundTripTimeMore5msLevelEntry 1}

psmDiameterRequestRoundTripTimeMore5msLevelVal OBJECT-TYPE
	SYNTAX     Counter64
	MAX-ACCESS read-only
	STATUS     current
	DESCRIPTION
	"Request round trip time > 5000ms"
	::={ psmDiameterRequestRoundTripTimeMore5msLevelEntry 2 }

psmDiameterRequestRoundTripTimeMore5msLevelMom OBJECT-TYPE
	SYNTAX     CounterBasedGauge64
	MAX-ACCESS read-only
	STATUS     current
	DESCRIPTION
	"Request round trip time > 5000ms"
	::={ psmDiameterRequestRoundTripTimeMore5msLevelEntry 3 }

psmDiameterRequestRoundTripTimeMore5msLevelMax OBJECT-TYPE
	SYNTAX     CounterBasedGauge64
	MAX-ACCESS read-only
	STATUS     current
	DESCRIPTION
	"Request round trip time > 5000ms"
	::={ psmDiameterRequestRoundTripTimeMore5msLevelEntry 4 }

psmDiameterRequestRoundTripTimeLess5ms OBJECT IDENTIFIER ::= { psmDiameter 38 }

psmDiameterRequestRoundTripTimeLess5msVal OBJECT-TYPE
	SYNTAX     Counter64
	MAX-ACCESS read-only
	STATUS     current
	DESCRIPTION "Request round trip time <= 500ms"

	::={ psmDiameterRequestRoundTripTimeLess5ms 1 }

psmDiameterRequestRoundTripTimeLess5msMom OBJECT-TYPE
	SYNTAX     CounterBasedGauge64
	MAX-ACCESS read-only
	STATUS     current
	DESCRIPTION "Request round trip time <= 500ms"

	::={ psmDiameterRequestRoundTripTimeLess5ms 2 }

psmDiameterRequestRoundTripTimeLess5msMax OBJECT-TYPE
	SYNTAX     CounterBasedGauge64
	MAX-ACCESS read-only
	STATUS     current
	DESCRIPTION "Request round trip time <= 500ms"

	::={ psmDiameterRequestRoundTripTimeLess5ms 3 }

psmDiameterRequestRoundTripTimeLess5msLevelTable OBJECT-TYPE
	SYNTAX     SEQUENCE OF PsmDiameterRequestRoundTripTimeLess5msLevelEntry
	MAX-ACCESS not-accessible
	STATUS     current
	DESCRIPTION
	"Request round trip time <= 500ms"
	::={ psmDiameterRequestRoundTripTimeLess5ms 4 }

psmDiameterRequestRoundTripTimeLess5msLevelEntry OBJECT-TYPE
	SYNTAX      PsmDiameterRequestRoundTripTimeLess5msLevelEntry
	MAX-ACCESS  not-accessible
	STATUS      current
	DESCRIPTION
	"Request round trip time <= 500ms"
	INDEX { psmDiameterRequestRoundTripTimeLess5msLevelName }
	::={ psmDiameterRequestRoundTripTimeLess5msLevelTable 1 }

PsmDiameterRequestRoundTripTimeLess5msLevelEntry ::=
	SEQUENCE {
		psmDiameterRequestRoundTripTimeLess5msLevelName DisplayString,
		psmDiameterRequestRoundTripTimeLess5msLevelVal  Counter64,
		psmDiameterRequestRoundTripTimeLess5msLevelMom  CounterBasedGauge64,
		psmDiameterRequestRoundTripTimeLess5msLevelMax  CounterBasedGauge64
	}

psmDiameterRequestRoundTripTimeLess5msLevelName OBJECT-TYPE
	SYNTAX      DisplayString
	MAX-ACCESS  not-accessible
	STATUS      current
	DESCRIPTION
	"Request round trip time <= 500ms"
	::={ psmDiameterRequestRoundTripTimeLess5msLevelEntry 1}

psmDiameterRequestRoundTripTimeLess5msLevelVal OBJECT-TYPE
	SYNTAX     Counter64
	MAX-ACCESS read-only
	STATUS     current
	DESCRIPTION
	"Request round trip time <= 500ms"
	::={ psmDiameterRequestRoundTripTimeLess5msLevelEntry 2 }

psmDiameterRequestRoundTripTimeLess5msLevelMom OBJECT-TYPE
	SYNTAX     CounterBasedGauge64
	MAX-ACCESS read-only
	STATUS     current
	DESCRIPTION
	"Request round trip time <= 500ms"
	::={ psmDiameterRequestRoundTripTimeLess5msLevelEntry 3 }

psmDiameterRequestRoundTripTimeLess5msLevelMax OBJECT-TYPE
	SYNTAX     CounterBasedGauge64
	MAX-ACCESS read-only
	STATUS     current
	DESCRIPTION
	"Request round trip time <= 500ms"
	::={ psmDiameterRequestRoundTripTimeLess5msLevelEntry 4 }

psmDiameterRequestRoundTripTimeLess5ms OBJECT IDENTIFIER ::= { psmDiameter 39 }

psmDiameterRequestRoundTripTimeLess5msVal OBJECT-TYPE
	SYNTAX     Counter64
	MAX-ACCESS read-only
	STATUS     current
	DESCRIPTION "Request round trip time <= 50ms"

	::={ psmDiameterRequestRoundTripTimeLess5ms 1 }

psmDiameterRequestRoundTripTimeLess5msMom OBJECT-TYPE
	SYNTAX     CounterBasedGauge64
	MAX-ACCESS read-only
	STATUS     current
	DESCRIPTION "Request round trip time <= 50ms"

	::={ psmDiameterRequestRoundTripTimeLess5ms 2 }

psmDiameterRequestRoundTripTimeLess5msMax OBJECT-TYPE
	SYNTAX     CounterBasedGauge64
	MAX-ACCESS read-only
	STATUS     current
	DESCRIPTION "Request round trip time <= 50ms"

	::={ psmDiameterRequestRoundTripTimeLess5ms 3 }

psmDiameterRequestRoundTripTimeLess5msLevelTable OBJECT-TYPE
	SYNTAX     SEQUENCE OF PsmDiameterRequestRoundTripTimeLess5msLevelEntry
	MAX-ACCESS not-accessible
	STATUS     current
	DESCRIPTION
	"Request round trip time <= 50ms"
	::={ psmDiameterRequestRoundTripTimeLess5ms 4 }

psmDiameterRequestRoundTripTimeLess5msLevelEntry OBJECT-TYPE
	SYNTAX      PsmDiameterRequestRoundTripTimeLess5msLevelEntry
	MAX-ACCESS  not-accessible
	STATUS      current
	DESCRIPTION
	"Request round trip time <= 50ms"
	INDEX { psmDiameterRequestRoundTripTimeLess5msLevelName }
	::={ psmDiameterRequestRoundTripTimeLess5msLevelTable 1 }

PsmDiameterRequestRoundTripTimeLess5msLevelEntry ::=
	SEQUENCE {
		psmDiameterRequestRoundTripTimeLess5msLevelName DisplayString,
		psmDiameterRequestRoundTripTimeLess5msLevelVal  Counter64,
		psmDiameterRequestRoundTripTimeLess5msLevelMom  CounterBasedGauge64,
		psmDiameterRequestRoundTripTimeLess5msLevelMax  CounterBasedGauge64
	}

psmDiameterRequestRoundTripTimeLess5msLevelName OBJECT-TYPE
	SYNTAX      DisplayString
	MAX-ACCESS  not-accessible
	STATUS      current
	DESCRIPTION
	"Request round trip time <= 50ms"
	::={ psmDiameterRequestRoundTripTimeLess5msLevelEntry 1}

psmDiameterRequestRoundTripTimeLess5msLevelVal OBJECT-TYPE
	SYNTAX     Counter64
	MAX-ACCESS read-only
	STATUS     current
	DESCRIPTION
	"Request round trip time <= 50ms"
	::={ psmDiameterRequestRoundTripTimeLess5msLevelEntry 2 }

psmDiameterRequestRoundTripTimeLess5msLevelMom OBJECT-TYPE
	SYNTAX     CounterBasedGauge64
	MAX-ACCESS read-only
	STATUS     current
	DESCRIPTION
	"Request round trip time <= 50ms"
	::={ psmDiameterRequestRoundTripTimeLess5msLevelEntry 3 }

psmDiameterRequestRoundTripTimeLess5msLevelMax OBJECT-TYPE
	SYNTAX     CounterBasedGauge64
	MAX-ACCESS read-only
	STATUS     current
	DESCRIPTION
	"Request round trip time <= 50ms"
	::={ psmDiameterRequestRoundTripTimeLess5msLevelEntry 4 }

psmDiameterState OBJECT IDENTIFIER ::= { psmDiameter 40 }

psmDiameterStateVal OBJECT-TYPE
	SYNTAX     INTEGER {
		disconnected(0),
		connecting(1),
		negotiating(2),
		online(3),
		disconnecting(4)
	}
	MAX-ACCESS read-only
	STATUS     current
	DESCRIPTION "State"

	::={ psmDiameterState 1 }

psmDiameterStateLevelTable OBJECT-TYPE
	SYNTAX     SEQUENCE OF PsmDiameterStateLevelEntry
	MAX-ACCESS not-accessible
	STATUS     current
	DESCRIPTION
	"State"
	::={ psmDiameterState 4 }

psmDiameterStateLevelEntry OBJECT-TYPE
	SYNTAX      PsmDiameterStateLevelEntry
	MAX-ACCESS  not-accessible
	STATUS      current
	DESCRIPTION
	"State"
	INDEX { psmDiameterStateLevelName }
	::={ psmDiameterStateLevelTable 1 }

PsmDiameterStateLevelEntry ::=
	SEQUENCE {
		psmDiameterStateLevelName DisplayString,
		psmDiameterStateLevelVal  INTEGER
	}

psmDiameterStateLevelName OBJECT-TYPE
	SYNTAX      DisplayString
	MAX-ACCESS  not-accessible
	STATUS      current
	DESCRIPTION
	"State"
	::={ psmDiameterStateLevelEntry 1}

psmDiameterStateLevelVal OBJECT-TYPE
	SYNTAX     INTEGER {
		disconnected(0),
		connecting(1),
		negotiating(2),
		online(3),
		disconnecting(4)
	}
	MAX-ACCESS read-only
	STATUS     current
	DESCRIPTION
	"State"
	::={ psmDiameterStateLevelEntry 2 }

psmDiameterUnknownAnswersReceived OBJECT IDENTIFIER ::= { psmDiameter 41 }

psmDiameterUnknownAnswersReceivedVal OBJECT-TYPE
	SYNTAX     Counter64
	MAX-ACCESS read-only
	STATUS     current
	DESCRIPTION "Unknown answers received"

	::={ psmDiameterUnknownAnswersReceived 1 }

psmDiameterUnknownAnswersReceivedMom OBJECT-TYPE
	SYNTAX     CounterBasedGauge64
	MAX-ACCESS read-only
	STATUS     current
	DESCRIPTION "Unknown answers received"

	::={ psmDiameterUnknownAnswersReceived 2 }

psmDiameterUnknownAnswersReceivedMax OBJECT-TYPE
	SYNTAX     CounterBasedGauge64
	MAX-ACCESS read-only
	STATUS     current
	DESCRIPTION "Unknown answers received"

	::={ psmDiameterUnknownAnswersReceived 3 }

psmDiameterUnknownAnswersReceivedLevelTable OBJECT-TYPE
	SYNTAX     SEQUENCE OF PsmDiameterUnknownAnswersReceivedLevelEntry
	MAX-ACCESS not-accessible
	STATUS     current
	DESCRIPTION
	"Unknown answers received"
	::={ psmDiameterUnknownAnswersReceived 4 }

psmDiameterUnknownAnswersReceivedLevelEntry OBJECT-TYPE
	SYNTAX      PsmDiameterUnknownAnswersReceivedLevelEntry
	MAX-ACCESS  not-accessible
	STATUS      current
	DESCRIPTION
	"Unknown answers received"
	INDEX { psmDiameterUnknownAnswersReceivedLevelName }
	::={ psmDiameterUnknownAnswersReceivedLevelTable 1 }

PsmDiameterUnknownAnswersReceivedLevelEntry ::=
	SEQUENCE {
		psmDiameterUnknownAnswersReceivedLevelName DisplayString,
		psmDiameterUnknownAnswersReceivedLevelVal  Counter64,
		psmDiameterUnknownAnswersReceivedLevelMom  CounterBasedGauge64,
		psmDiameterUnknownAnswersReceivedLevelMax  CounterBasedGauge64
	}

psmDiameterUnknownAnswersReceivedLevelName OBJECT-TYPE
	SYNTAX      DisplayString
	MAX-ACCESS  not-accessible
	STATUS      current
	DESCRIPTION
	"Unknown answers received"
	::={ psmDiameterUnknownAnswersReceivedLevelEntry 1}

psmDiameterUnknownAnswersReceivedLevelVal OBJECT-TYPE
	SYNTAX     Counter64
	MAX-ACCESS read-only
	STATUS     current
	DESCRIPTION
	"Unknown answers received"
	::={ psmDiameterUnknownAnswersReceivedLevelEntry 2 }

psmDiameterUnknownAnswersReceivedLevelMom OBJECT-TYPE
	SYNTAX     CounterBasedGauge64
	MAX-ACCESS read-only
	STATUS     current
	DESCRIPTION
	"Unknown answers received"
	::={ psmDiameterUnknownAnswersReceivedLevelEntry 3 }

psmDiameterUnknownAnswersReceivedLevelMax OBJECT-TYPE
	SYNTAX     CounterBasedGauge64
	MAX-ACCESS read-only
	STATUS     current
	DESCRIPTION
	"Unknown answers received"
	::={ psmDiameterUnknownAnswersReceivedLevelEntry 4 }

psmDiameterUnknownRequestsReceived OBJECT IDENTIFIER ::= { psmDiameter 42 }

psmDiameterUnknownRequestsReceivedVal OBJECT-TYPE
	SYNTAX     Counter64
	MAX-ACCESS read-only
	STATUS     current
	DESCRIPTION "Unknown requests received"

	::={ psmDiameterUnknownRequestsReceived 1 }

psmDiameterUnknownRequestsReceivedMom OBJECT-TYPE
	SYNTAX     CounterBasedGauge64
	MAX-ACCESS read-only
	STATUS     current
	DESCRIPTION "Unknown requests received"

	::={ psmDiameterUnknownRequestsReceived 2 }

psmDiameterUnknownRequestsReceivedMax OBJECT-TYPE
	SYNTAX     CounterBasedGauge64
	MAX-ACCESS read-only
	STATUS     current
	DESCRIPTION "Unknown requests received"

	::={ psmDiameterUnknownRequestsReceived 3 }

psmDiameterUnknownRequestsReceivedLevelTable OBJECT-TYPE
	SYNTAX     SEQUENCE OF PsmDiameterUnknownRequestsReceivedLevelEntry
	MAX-ACCESS not-accessible
	STATUS     current
	DESCRIPTION
	"Unknown requests received"
	::={ psmDiameterUnknownRequestsReceived 4 }

psmDiameterUnknownRequestsReceivedLevelEntry OBJECT-TYPE
	SYNTAX      PsmDiameterUnknownRequestsReceivedLevelEntry
	MAX-ACCESS  not-accessible
	STATUS      current
	DESCRIPTION
	"Unknown requests received"
	INDEX { psmDiameterUnknownRequestsReceivedLevelName }
	::={ psmDiameterUnknownRequestsReceivedLevelTable 1 }

PsmDiameterUnknownRequestsReceivedLevelEntry ::=
	SEQUENCE {
		psmDiameterUnknownRequestsReceivedLevelName DisplayString,
		psmDiameterUnknownRequestsReceivedLevelVal  Counter64,
		psmDiameterUnknownRequestsReceivedLevelMom  CounterBasedGauge64,
		psmDiameterUnknownRequestsReceivedLevelMax  CounterBasedGauge64
	}

psmDiameterUnknownRequestsReceivedLevelName OBJECT-TYPE
	SYNTAX      DisplayString
	MAX-ACCESS  not-accessible
	STATUS      current
	DESCRIPTION
	"Unknown requests received"
	::={ psmDiameterUnknownRequestsReceivedLevelEntry 1}

psmDiameterUnknownRequestsReceivedLevelVal OBJECT-TYPE
	SYNTAX     Counter64
	MAX-ACCESS read-only
	STATUS     current
	DESCRIPTION
	"Unknown requests received"
	::={ psmDiameterUnknownRequestsReceivedLevelEntry 2 }

psmDiameterUnknownRequestsReceivedLevelMom OBJECT-TYPE
	SYNTAX     CounterBasedGauge64
	MAX-ACCESS read-only
	STATUS     current
	DESCRIPTION
	"Unknown requests received"
	::={ psmDiameterUnknownRequestsReceivedLevelEntry 3 }

psmDiameterUnknownRequestsReceivedLevelMax OBJECT-TYPE
	SYNTAX     CounterBasedGauge64
	MAX-ACCESS read-only
	STATUS     current
	DESCRIPTION
	"Unknown requests received"
	::={ psmDiameterUnknownRequestsReceivedLevelEntry 4 }

psmProvisionerOld OBJECT IDENTIFIER ::= { psmv2 3 }

psmProvisionerOldStaticRulesetUpdates OBJECT IDENTIFIER ::= { psmProvisionerOld 1 }

psmProvisionerOldStaticRulesetUpdatesVal OBJECT-TYPE
	SYNTAX     Counter64
	MAX-ACCESS read-only
	STATUS     current
	DESCRIPTION "Static ruleset updates"

	::={ psmProvisionerOldStaticRulesetUpdates 1 }

psmProvisionerOldStaticRulesetUpdatesMom OBJECT-TYPE
	SYNTAX     CounterBasedGauge64
	MAX-ACCESS read-only
	STATUS     current
	DESCRIPTION "Static ruleset updates"

	::={ psmProvisionerOldStaticRulesetUpdates 2 }

psmProvisionerOldStaticRulesetUpdatesMax OBJECT-TYPE
	SYNTAX     CounterBasedGauge64
	MAX-ACCESS read-only
	STATUS     current
	DESCRIPTION "Static ruleset updates"

	::={ psmProvisionerOldStaticRulesetUpdates 3 }

psmProvisionerOldStaticRulesetUpdatesLevelTable OBJECT-TYPE
	SYNTAX     SEQUENCE OF PsmProvisionerOldStaticRulesetUpdatesLevelEntry
	MAX-ACCESS not-accessible
	STATUS     current
	DESCRIPTION
	"Static ruleset updates"
	::={ psmProvisionerOldStaticRulesetUpdates 4 }

psmProvisionerOldStaticRulesetUpdatesLevelEntry OBJECT-TYPE
	SYNTAX      PsmProvisionerOldStaticRulesetUpdatesLevelEntry
	MAX-ACCESS  not-accessible
	STATUS      current
	DESCRIPTION
	"Static ruleset updates"
	INDEX { psmProvisionerOldStaticRulesetUpdatesLevelName }
	::={ psmProvisionerOldStaticRulesetUpdatesLevelTable 1 }

PsmProvisionerOldStaticRulesetUpdatesLevelEntry ::=
	SEQUENCE {
		psmProvisionerOldStaticRulesetUpdatesLevelName DisplayString,
		psmProvisionerOldStaticRulesetUpdatesLevelVal  Counter64,
		psmProvisionerOldStaticRulesetUpdatesLevelMom  CounterBasedGauge64,
		psmProvisionerOldStaticRulesetUpdatesLevelMax  CounterBasedGauge64
	}

psmProvisionerOldStaticRulesetUpdatesLevelName OBJECT-TYPE
	SYNTAX      DisplayString
	MAX-ACCESS  not-accessible
	STATUS      current
	DESCRIPTION
	"Static ruleset updates"
	::={ psmProvisionerOldStaticRulesetUpdatesLevelEntry 1}

psmProvisionerOldStaticRulesetUpdatesLevelVal OBJECT-TYPE
	SYNTAX     Counter64
	MAX-ACCESS read-only
	STATUS     current
	DESCRIPTION
	"Static ruleset updates"
	::={ psmProvisionerOldStaticRulesetUpdatesLevelEntry 2 }

psmProvisionerOldStaticRulesetUpdatesLevelMom OBJECT-TYPE
	SYNTAX     CounterBasedGauge64
	MAX-ACCESS read-only
	STATUS     current
	DESCRIPTION
	"Static ruleset updates"
	::={ psmProvisionerOldStaticRulesetUpdatesLevelEntry 3 }

psmProvisionerOldStaticRulesetUpdatesLevelMax OBJECT-TYPE
	SYNTAX     CounterBasedGauge64
	MAX-ACCESS read-only
	STATUS     current
	DESCRIPTION
	"Static ruleset updates"
	::={ psmProvisionerOldStaticRulesetUpdatesLevelEntry 4 }

psmProvisionerOldProxyGroupEnabled OBJECT IDENTIFIER ::= { psmProvisionerOld 2 }

psmProvisionerOldProxyGroupEnabledVal OBJECT-TYPE
	SYNTAX     INTEGER {
		false(0),
		true(1)
	}
	MAX-ACCESS read-only
	STATUS     current
	DESCRIPTION "Proxy group enabled"

	::={ psmProvisionerOldProxyGroupEnabled 1 }

psmProvisionerOldProxyGroupEnabledLevelTable OBJECT-TYPE
	SYNTAX     SEQUENCE OF PsmProvisionerOldProxyGroupEnabledLevelEntry
	MAX-ACCESS not-accessible
	STATUS     current
	DESCRIPTION
	"Proxy group enabled"
	::={ psmProvisionerOldProxyGroupEnabled 4 }

psmProvisionerOldProxyGroupEnabledLevelEntry OBJECT-TYPE
	SYNTAX      PsmProvisionerOldProxyGroupEnabledLevelEntry
	MAX-ACCESS  not-accessible
	STATUS      current
	DESCRIPTION
	"Proxy group enabled"
	INDEX { psmProvisionerOldProxyGroupEnabledLevelName }
	::={ psmProvisionerOldProxyGroupEnabledLevelTable 1 }

PsmProvisionerOldProxyGroupEnabledLevelEntry ::=
	SEQUENCE {
		psmProvisionerOldProxyGroupEnabledLevelName DisplayString,
		psmProvisionerOldProxyGroupEnabledLevelVal  INTEGER
	}

psmProvisionerOldProxyGroupEnabledLevelName OBJECT-TYPE
	SYNTAX      DisplayString
	MAX-ACCESS  not-accessible
	STATUS      current
	DESCRIPTION
	"Proxy group enabled"
	::={ psmProvisionerOldProxyGroupEnabledLevelEntry 1}

psmProvisionerOldProxyGroupEnabledLevelVal OBJECT-TYPE
	SYNTAX     INTEGER {
		false(0),
		true(1)
	}
	MAX-ACCESS read-only
	STATUS     current
	DESCRIPTION
	"Proxy group enabled"
	::={ psmProvisionerOldProxyGroupEnabledLevelEntry 2 }

psmProvisionerOldProxyGroupEventCount OBJECT IDENTIFIER ::= { psmProvisionerOld 3 }

psmProvisionerOldProxyGroupEventCountVal OBJECT-TYPE
	SYNTAX     Counter64
	MAX-ACCESS read-only
	STATUS     current
	DESCRIPTION "Proxy group event count"

	::={ psmProvisionerOldProxyGroupEventCount 1 }

psmProvisionerOldProxyGroupEventCountMom OBJECT-TYPE
	SYNTAX     CounterBasedGauge64
	MAX-ACCESS read-only
	STATUS     current
	DESCRIPTION "Proxy group event count"

	::={ psmProvisionerOldProxyGroupEventCount 2 }

psmProvisionerOldProxyGroupEventCountMax OBJECT-TYPE
	SYNTAX     CounterBasedGauge64
	MAX-ACCESS read-only
	STATUS     current
	DESCRIPTION "Proxy group event count"

	::={ psmProvisionerOldProxyGroupEventCount 3 }

psmProvisionerOldProxyGroupEventCountLevelTable OBJECT-TYPE
	SYNTAX     SEQUENCE OF PsmProvisionerOldProxyGroupEventCountLevelEntry
	MAX-ACCESS not-accessible
	STATUS     current
	DESCRIPTION
	"Proxy group event count"
	::={ psmProvisionerOldProxyGroupEventCount 4 }

psmProvisionerOldProxyGroupEventCountLevelEntry OBJECT-TYPE
	SYNTAX      PsmProvisionerOldProxyGroupEventCountLevelEntry
	MAX-ACCESS  not-accessible
	STATUS      current
	DESCRIPTION
	"Proxy group event count"
	INDEX { psmProvisionerOldProxyGroupEventCountLevelName }
	::={ psmProvisionerOldProxyGroupEventCountLevelTable 1 }

PsmProvisionerOldProxyGroupEventCountLevelEntry ::=
	SEQUENCE {
		psmProvisionerOldProxyGroupEventCountLevelName DisplayString,
		psmProvisionerOldProxyGroupEventCountLevelVal  Counter64,
		psmProvisionerOldProxyGroupEventCountLevelMom  CounterBasedGauge64,
		psmProvisionerOldProxyGroupEventCountLevelMax  CounterBasedGauge64
	}

psmProvisionerOldProxyGroupEventCountLevelName OBJECT-TYPE
	SYNTAX      DisplayString
	MAX-ACCESS  not-accessible
	STATUS      current
	DESCRIPTION
	"Proxy group event count"
	::={ psmProvisionerOldProxyGroupEventCountLevelEntry 1}

psmProvisionerOldProxyGroupEventCountLevelVal OBJECT-TYPE
	SYNTAX     Counter64
	MAX-ACCESS read-only
	STATUS     current
	DESCRIPTION
	"Proxy group event count"
	::={ psmProvisionerOldProxyGroupEventCountLevelEntry 2 }

psmProvisionerOldProxyGroupEventCountLevelMom OBJECT-TYPE
	SYNTAX     CounterBasedGauge64
	MAX-ACCESS read-only
	STATUS     current
	DESCRIPTION
	"Proxy group event count"
	::={ psmProvisionerOldProxyGroupEventCountLevelEntry 3 }

psmProvisionerOldProxyGroupEventCountLevelMax OBJECT-TYPE
	SYNTAX     CounterBasedGauge64
	MAX-ACCESS read-only
	STATUS     current
	DESCRIPTION
	"Proxy group event count"
	::={ psmProvisionerOldProxyGroupEventCountLevelEntry 4 }

psmProvisionerOldProxyGroupEventQueueSize OBJECT IDENTIFIER ::= { psmProvisionerOld 4 }

psmProvisionerOldProxyGroupEventQueueSizeVal OBJECT-TYPE
	SYNTAX     CounterBasedGauge64
	MAX-ACCESS read-only
	STATUS     current
	DESCRIPTION "Proxy group event queue size"

	::={ psmProvisionerOldProxyGroupEventQueueSize 1 }

psmProvisionerOldProxyGroupEventQueueSizeMax OBJECT-TYPE
	SYNTAX     CounterBasedGauge64
	MAX-ACCESS read-only
	STATUS     current
	DESCRIPTION "Proxy group event queue size"

	::={ psmProvisionerOldProxyGroupEventQueueSize 3 }

psmProvisionerOldProxyGroupEventQueueSizeLevelTable OBJECT-TYPE
	SYNTAX     SEQUENCE OF PsmProvisionerOldProxyGroupEventQueueSizeLevelEntry
	MAX-ACCESS not-accessible
	STATUS     current
	DESCRIPTION
	"Proxy group event queue size"
	::={ psmProvisionerOldProxyGroupEventQueueSize 4 }

psmProvisionerOldProxyGroupEventQueueSizeLevelEntry OBJECT-TYPE
	SYNTAX      PsmProvisionerOldProxyGroupEventQueueSizeLevelEntry
	MAX-ACCESS  not-accessible
	STATUS      current
	DESCRIPTION
	"Proxy group event queue size"
	INDEX { psmProvisionerOldProxyGroupEventQueueSizeLevelName }
	::={ psmProvisionerOldProxyGroupEventQueueSizeLevelTable 1 }

PsmProvisionerOldProxyGroupEventQueueSizeLevelEntry ::=
	SEQUENCE {
		psmProvisionerOldProxyGroupEventQueueSizeLevelName DisplayString,
		psmProvisionerOldProxyGroupEventQueueSizeLevelVal  CounterBasedGauge64,
		psmProvisionerOldProxyGroupEventQueueSizeLevelMax  CounterBasedGauge64
	}

psmProvisionerOldProxyGroupEventQueueSizeLevelName OBJECT-TYPE
	SYNTAX      DisplayString
	MAX-ACCESS  not-accessible
	STATUS      current
	DESCRIPTION
	"Proxy group event queue size"
	::={ psmProvisionerOldProxyGroupEventQueueSizeLevelEntry 1}

psmProvisionerOldProxyGroupEventQueueSizeLevelVal OBJECT-TYPE
	SYNTAX     CounterBasedGauge64
	MAX-ACCESS read-only
	STATUS     current
	DESCRIPTION
	"Proxy group event queue size"
	::={ psmProvisionerOldProxyGroupEventQueueSizeLevelEntry 2 }

psmProvisionerOldProxyGroupEventQueueSizeLevelMax OBJECT-TYPE
	SYNTAX     CounterBasedGauge64
	MAX-ACCESS read-only
	STATUS     current
	DESCRIPTION
	"Proxy group event queue size"
	::={ psmProvisionerOldProxyGroupEventQueueSizeLevelEntry 4 }

psmProvisionerOldStaticRulesetBacklogSize OBJECT IDENTIFIER ::= { psmProvisionerOld 5 }

psmProvisionerOldStaticRulesetBacklogSizeVal OBJECT-TYPE
	SYNTAX     CounterBasedGauge64
	MAX-ACCESS read-only
	STATUS     current
	DESCRIPTION "Static ruleset backlog size"

	::={ psmProvisionerOldStaticRulesetBacklogSize 1 }

psmProvisionerOldStaticRulesetBacklogSizeMax OBJECT-TYPE
	SYNTAX     CounterBasedGauge64
	MAX-ACCESS read-only
	STATUS     current
	DESCRIPTION "Static ruleset backlog size"

	::={ psmProvisionerOldStaticRulesetBacklogSize 3 }

psmProvisionerOldStaticRulesetBacklogSizeLevelTable OBJECT-TYPE
	SYNTAX     SEQUENCE OF PsmProvisionerOldStaticRulesetBacklogSizeLevelEntry
	MAX-ACCESS not-accessible
	STATUS     current
	DESCRIPTION
	"Static ruleset backlog size"
	::={ psmProvisionerOldStaticRulesetBacklogSize 4 }

psmProvisionerOldStaticRulesetBacklogSizeLevelEntry OBJECT-TYPE
	SYNTAX      PsmProvisionerOldStaticRulesetBacklogSizeLevelEntry
	MAX-ACCESS  not-accessible
	STATUS      current
	DESCRIPTION
	"Static ruleset backlog size"
	INDEX { psmProvisionerOldStaticRulesetBacklogSizeLevelName }
	::={ psmProvisionerOldStaticRulesetBacklogSizeLevelTable 1 }

PsmProvisionerOldStaticRulesetBacklogSizeLevelEntry ::=
	SEQUENCE {
		psmProvisionerOldStaticRulesetBacklogSizeLevelName DisplayString,
		psmProvisionerOldStaticRulesetBacklogSizeLevelVal  CounterBasedGauge64,
		psmProvisionerOldStaticRulesetBacklogSizeLevelMax  CounterBasedGauge64
	}

psmProvisionerOldStaticRulesetBacklogSizeLevelName OBJECT-TYPE
	SYNTAX      DisplayString
	MAX-ACCESS  not-accessible
	STATUS      current
	DESCRIPTION
	"Static ruleset backlog size"
	::={ psmProvisionerOldStaticRulesetBacklogSizeLevelEntry 1}

psmProvisionerOldStaticRulesetBacklogSizeLevelVal OBJECT-TYPE
	SYNTAX     CounterBasedGauge64
	MAX-ACCESS read-only
	STATUS     current
	DESCRIPTION
	"Static ruleset backlog size"
	::={ psmProvisionerOldStaticRulesetBacklogSizeLevelEntry 2 }

psmProvisionerOldStaticRulesetBacklogSizeLevelMax OBJECT-TYPE
	SYNTAX     CounterBasedGauge64
	MAX-ACCESS read-only
	STATUS     current
	DESCRIPTION
	"Static ruleset backlog size"
	::={ psmProvisionerOldStaticRulesetBacklogSizeLevelEntry 4 }

psmProvisionerOldStaticRulesetCommits OBJECT IDENTIFIER ::= { psmProvisionerOld 6 }

psmProvisionerOldStaticRulesetCommitsVal OBJECT-TYPE
	SYNTAX     Counter64
	MAX-ACCESS read-only
	STATUS     current
	DESCRIPTION "Static ruleset commits"

	::={ psmProvisionerOldStaticRulesetCommits 1 }

psmProvisionerOldStaticRulesetCommitsMom OBJECT-TYPE
	SYNTAX     CounterBasedGauge64
	MAX-ACCESS read-only
	STATUS     current
	DESCRIPTION "Static ruleset commits"

	::={ psmProvisionerOldStaticRulesetCommits 2 }

psmProvisionerOldStaticRulesetCommitsMax OBJECT-TYPE
	SYNTAX     CounterBasedGauge64
	MAX-ACCESS read-only
	STATUS     current
	DESCRIPTION "Static ruleset commits"

	::={ psmProvisionerOldStaticRulesetCommits 3 }

psmProvisionerOldStaticRulesetCommitsLevelTable OBJECT-TYPE
	SYNTAX     SEQUENCE OF PsmProvisionerOldStaticRulesetCommitsLevelEntry
	MAX-ACCESS not-accessible
	STATUS     current
	DESCRIPTION
	"Static ruleset commits"
	::={ psmProvisionerOldStaticRulesetCommits 4 }

psmProvisionerOldStaticRulesetCommitsLevelEntry OBJECT-TYPE
	SYNTAX      PsmProvisionerOldStaticRulesetCommitsLevelEntry
	MAX-ACCESS  not-accessible
	STATUS      current
	DESCRIPTION
	"Static ruleset commits"
	INDEX { psmProvisionerOldStaticRulesetCommitsLevelName }
	::={ psmProvisionerOldStaticRulesetCommitsLevelTable 1 }

PsmProvisionerOldStaticRulesetCommitsLevelEntry ::=
	SEQUENCE {
		psmProvisionerOldStaticRulesetCommitsLevelName DisplayString,
		psmProvisionerOldStaticRulesetCommitsLevelVal  Counter64,
		psmProvisionerOldStaticRulesetCommitsLevelMom  CounterBasedGauge64,
		psmProvisionerOldStaticRulesetCommitsLevelMax  CounterBasedGauge64
	}

psmProvisionerOldStaticRulesetCommitsLevelName OBJECT-TYPE
	SYNTAX      DisplayString
	MAX-ACCESS  not-accessible
	STATUS      current
	DESCRIPTION
	"Static ruleset commits"
	::={ psmProvisionerOldStaticRulesetCommitsLevelEntry 1}

psmProvisionerOldStaticRulesetCommitsLevelVal OBJECT-TYPE
	SYNTAX     Counter64
	MAX-ACCESS read-only
	STATUS     current
	DESCRIPTION
	"Static ruleset commits"
	::={ psmProvisionerOldStaticRulesetCommitsLevelEntry 2 }

psmProvisionerOldStaticRulesetCommitsLevelMom OBJECT-TYPE
	SYNTAX     CounterBasedGauge64
	MAX-ACCESS read-only
	STATUS     current
	DESCRIPTION
	"Static ruleset commits"
	::={ psmProvisionerOldStaticRulesetCommitsLevelEntry 3 }

psmProvisionerOldStaticRulesetCommitsLevelMax OBJECT-TYPE
	SYNTAX     CounterBasedGauge64
	MAX-ACCESS read-only
	STATUS     current
	DESCRIPTION
	"Static ruleset commits"
	::={ psmProvisionerOldStaticRulesetCommitsLevelEntry 4 }

psmProvisionerOldStaticRulesetEnabled OBJECT IDENTIFIER ::= { psmProvisionerOld 7 }

psmProvisionerOldStaticRulesetEnabledVal OBJECT-TYPE
	SYNTAX     INTEGER {
		false(0),
		true(1)
	}
	MAX-ACCESS read-only
	STATUS     current
	DESCRIPTION "Static ruleset enabled"

	::={ psmProvisionerOldStaticRulesetEnabled 1 }

psmProvisionerOldStaticRulesetEnabledLevelTable OBJECT-TYPE
	SYNTAX     SEQUENCE OF PsmProvisionerOldStaticRulesetEnabledLevelEntry
	MAX-ACCESS not-accessible
	STATUS     current
	DESCRIPTION
	"Static ruleset enabled"
	::={ psmProvisionerOldStaticRulesetEnabled 4 }

psmProvisionerOldStaticRulesetEnabledLevelEntry OBJECT-TYPE
	SYNTAX      PsmProvisionerOldStaticRulesetEnabledLevelEntry
	MAX-ACCESS  not-accessible
	STATUS      current
	DESCRIPTION
	"Static ruleset enabled"
	INDEX { psmProvisionerOldStaticRulesetEnabledLevelName }
	::={ psmProvisionerOldStaticRulesetEnabledLevelTable 1 }

PsmProvisionerOldStaticRulesetEnabledLevelEntry ::=
	SEQUENCE {
		psmProvisionerOldStaticRulesetEnabledLevelName DisplayString,
		psmProvisionerOldStaticRulesetEnabledLevelVal  INTEGER
	}

psmProvisionerOldStaticRulesetEnabledLevelName OBJECT-TYPE
	SYNTAX      DisplayString
	MAX-ACCESS  not-accessible
	STATUS      current
	DESCRIPTION
	"Static ruleset enabled"
	::={ psmProvisionerOldStaticRulesetEnabledLevelEntry 1}

psmProvisionerOldStaticRulesetEnabledLevelVal OBJECT-TYPE
	SYNTAX     INTEGER {
		false(0),
		true(1)
	}
	MAX-ACCESS read-only
	STATUS     current
	DESCRIPTION
	"Static ruleset enabled"
	::={ psmProvisionerOldStaticRulesetEnabledLevelEntry 2 }

psmProvisionerOldStaticRulesetCommitTime OBJECT IDENTIFIER ::= { psmProvisionerOld 8 }

psmProvisionerOldStaticRulesetCommitTimeVal OBJECT-TYPE
	SYNTAX     DateAndTime
	MAX-ACCESS read-only
	STATUS     current
	DESCRIPTION "Static ruleset commit time"

	::={ psmProvisionerOldStaticRulesetCommitTime 1 }

psmProvisionerOldStaticRulesetCommitTimeLevelTable OBJECT-TYPE
	SYNTAX     SEQUENCE OF PsmProvisionerOldStaticRulesetCommitTimeLevelEntry
	MAX-ACCESS not-accessible
	STATUS     current
	DESCRIPTION
	"Static ruleset commit time"
	::={ psmProvisionerOldStaticRulesetCommitTime 4 }

psmProvisionerOldStaticRulesetCommitTimeLevelEntry OBJECT-TYPE
	SYNTAX      PsmProvisionerOldStaticRulesetCommitTimeLevelEntry
	MAX-ACCESS  not-accessible
	STATUS      current
	DESCRIPTION
	"Static ruleset commit time"
	INDEX { psmProvisionerOldStaticRulesetCommitTimeLevelName }
	::={ psmProvisionerOldStaticRulesetCommitTimeLevelTable 1 }

PsmProvisionerOldStaticRulesetCommitTimeLevelEntry ::=
	SEQUENCE {
		psmProvisionerOldStaticRulesetCommitTimeLevelName DisplayString,
		psmProvisionerOldStaticRulesetCommitTimeLevelVal  DateAndTime
	}

psmProvisionerOldStaticRulesetCommitTimeLevelName OBJECT-TYPE
	SYNTAX      DisplayString
	MAX-ACCESS  not-accessible
	STATUS      current
	DESCRIPTION
	"Static ruleset commit time"
	::={ psmProvisionerOldStaticRulesetCommitTimeLevelEntry 1}

psmProvisionerOldStaticRulesetCommitTimeLevelVal OBJECT-TYPE
	SYNTAX     DateAndTime
	MAX-ACCESS read-only
	STATUS     current
	DESCRIPTION
	"Static ruleset commit time"
	::={ psmProvisionerOldStaticRulesetCommitTimeLevelEntry 2 }

psmProvisionerOldStaticRulesetRollbackTime OBJECT IDENTIFIER ::= { psmProvisionerOld 9 }

psmProvisionerOldStaticRulesetRollbackTimeVal OBJECT-TYPE
	SYNTAX     DateAndTime
	MAX-ACCESS read-only
	STATUS     current
	DESCRIPTION "Static ruleset rollback time"

	::={ psmProvisionerOldStaticRulesetRollbackTime 1 }

psmProvisionerOldStaticRulesetRollbackTimeLevelTable OBJECT-TYPE
	SYNTAX     SEQUENCE OF PsmProvisionerOldStaticRulesetRollbackTimeLevelEntry
	MAX-ACCESS not-accessible
	STATUS     current
	DESCRIPTION
	"Static ruleset rollback time"
	::={ psmProvisionerOldStaticRulesetRollbackTime 4 }

psmProvisionerOldStaticRulesetRollbackTimeLevelEntry OBJECT-TYPE
	SYNTAX      PsmProvisionerOldStaticRulesetRollbackTimeLevelEntry
	MAX-ACCESS  not-accessible
	STATUS      current
	DESCRIPTION
	"Static ruleset rollback time"
	INDEX { psmProvisionerOldStaticRulesetRollbackTimeLevelName }
	::={ psmProvisionerOldStaticRulesetRollbackTimeLevelTable 1 }

PsmProvisionerOldStaticRulesetRollbackTimeLevelEntry ::=
	SEQUENCE {
		psmProvisionerOldStaticRulesetRollbackTimeLevelName DisplayString,
		psmProvisionerOldStaticRulesetRollbackTimeLevelVal  DateAndTime
	}

psmProvisionerOldStaticRulesetRollbackTimeLevelName OBJECT-TYPE
	SYNTAX      DisplayString
	MAX-ACCESS  not-accessible
	STATUS      current
	DESCRIPTION
	"Static ruleset rollback time"
	::={ psmProvisionerOldStaticRulesetRollbackTimeLevelEntry 1}

psmProvisionerOldStaticRulesetRollbackTimeLevelVal OBJECT-TYPE
	SYNTAX     DateAndTime
	MAX-ACCESS read-only
	STATUS     current
	DESCRIPTION
	"Static ruleset rollback time"
	::={ psmProvisionerOldStaticRulesetRollbackTimeLevelEntry 2 }

psmProvisionerOldStaticRulesetStateChange OBJECT IDENTIFIER ::= { psmProvisionerOld 10 }

psmProvisionerOldStaticRulesetStateChangeVal OBJECT-TYPE
	SYNTAX     DateAndTime
	MAX-ACCESS read-only
	STATUS     current
	DESCRIPTION "Static ruleset state change"

	::={ psmProvisionerOldStaticRulesetStateChange 1 }

psmProvisionerOldStaticRulesetStateChangeLevelTable OBJECT-TYPE
	SYNTAX     SEQUENCE OF PsmProvisionerOldStaticRulesetStateChangeLevelEntry
	MAX-ACCESS not-accessible
	STATUS     current
	DESCRIPTION
	"Static ruleset state change"
	::={ psmProvisionerOldStaticRulesetStateChange 4 }

psmProvisionerOldStaticRulesetStateChangeLevelEntry OBJECT-TYPE
	SYNTAX      PsmProvisionerOldStaticRulesetStateChangeLevelEntry
	MAX-ACCESS  not-accessible
	STATUS      current
	DESCRIPTION
	"Static ruleset state change"
	INDEX { psmProvisionerOldStaticRulesetStateChangeLevelName }
	::={ psmProvisionerOldStaticRulesetStateChangeLevelTable 1 }

PsmProvisionerOldStaticRulesetStateChangeLevelEntry ::=
	SEQUENCE {
		psmProvisionerOldStaticRulesetStateChangeLevelName DisplayString,
		psmProvisionerOldStaticRulesetStateChangeLevelVal  DateAndTime
	}

psmProvisionerOldStaticRulesetStateChangeLevelName OBJECT-TYPE
	SYNTAX      DisplayString
	MAX-ACCESS  not-accessible
	STATUS      current
	DESCRIPTION
	"Static ruleset state change"
	::={ psmProvisionerOldStaticRulesetStateChangeLevelEntry 1}

psmProvisionerOldStaticRulesetStateChangeLevelVal OBJECT-TYPE
	SYNTAX     DateAndTime
	MAX-ACCESS read-only
	STATUS     current
	DESCRIPTION
	"Static ruleset state change"
	::={ psmProvisionerOldStaticRulesetStateChangeLevelEntry 2 }

psmProvisionerOldStaticRulesetNextReconnectTime OBJECT IDENTIFIER ::= { psmProvisionerOld 11 }

psmProvisionerOldStaticRulesetNextReconnectTimeVal OBJECT-TYPE
	SYNTAX     DateAndTime
	MAX-ACCESS read-only
	STATUS     current
	DESCRIPTION "Static ruleset next reconnect time"

	::={ psmProvisionerOldStaticRulesetNextReconnectTime 1 }

psmProvisionerOldStaticRulesetNextReconnectTimeLevelTable OBJECT-TYPE
	SYNTAX     SEQUENCE OF PsmProvisionerOldStaticRulesetNextReconnectTimeLevelEntry
	MAX-ACCESS not-accessible
	STATUS     current
	DESCRIPTION
	"Static ruleset next reconnect time"
	::={ psmProvisionerOldStaticRulesetNextReconnectTime 4 }

psmProvisionerOldStaticRulesetNextReconnectTimeLevelEntry OBJECT-TYPE
	SYNTAX      PsmProvisionerOldStaticRulesetNextReconnectTimeLevelEntry
	MAX-ACCESS  not-accessible
	STATUS      current
	DESCRIPTION
	"Static ruleset next reconnect time"
	INDEX { psmProvisionerOldStaticRulesetNextReconnectTimeLevelName }
	::={ psmProvisionerOldStaticRulesetNextReconnectTimeLevelTable 1 }

PsmProvisionerOldStaticRulesetNextReconnectTimeLevelEntry ::=
	SEQUENCE {
		psmProvisionerOldStaticRulesetNextReconnectTimeLevelName DisplayString,
		psmProvisionerOldStaticRulesetNextReconnectTimeLevelVal  DateAndTime
	}

psmProvisionerOldStaticRulesetNextReconnectTimeLevelName OBJECT-TYPE
	SYNTAX      DisplayString
	MAX-ACCESS  not-accessible
	STATUS      current
	DESCRIPTION
	"Static ruleset next reconnect time"
	::={ psmProvisionerOldStaticRulesetNextReconnectTimeLevelEntry 1}

psmProvisionerOldStaticRulesetNextReconnectTimeLevelVal OBJECT-TYPE
	SYNTAX     DateAndTime
	MAX-ACCESS read-only
	STATUS     current
	DESCRIPTION
	"Static ruleset next reconnect time"
	::={ psmProvisionerOldStaticRulesetNextReconnectTimeLevelEntry 2 }

psmProvisionerOldStaticRulesetReconnects OBJECT IDENTIFIER ::= { psmProvisionerOld 12 }

psmProvisionerOldStaticRulesetReconnectsVal OBJECT-TYPE
	SYNTAX     Counter64
	MAX-ACCESS read-only
	STATUS     current
	DESCRIPTION "Static ruleset reconnects"

	::={ psmProvisionerOldStaticRulesetReconnects 1 }

psmProvisionerOldStaticRulesetReconnectsMom OBJECT-TYPE
	SYNTAX     CounterBasedGauge64
	MAX-ACCESS read-only
	STATUS     current
	DESCRIPTION "Static ruleset reconnects"

	::={ psmProvisionerOldStaticRulesetReconnects 2 }

psmProvisionerOldStaticRulesetReconnectsMax OBJECT-TYPE
	SYNTAX     CounterBasedGauge64
	MAX-ACCESS read-only
	STATUS     current
	DESCRIPTION "Static ruleset reconnects"

	::={ psmProvisionerOldStaticRulesetReconnects 3 }

psmProvisionerOldStaticRulesetReconnectsLevelTable OBJECT-TYPE
	SYNTAX     SEQUENCE OF PsmProvisionerOldStaticRulesetReconnectsLevelEntry
	MAX-ACCESS not-accessible
	STATUS     current
	DESCRIPTION
	"Static ruleset reconnects"
	::={ psmProvisionerOldStaticRulesetReconnects 4 }

psmProvisionerOldStaticRulesetReconnectsLevelEntry OBJECT-TYPE
	SYNTAX      PsmProvisionerOldStaticRulesetReconnectsLevelEntry
	MAX-ACCESS  not-accessible
	STATUS      current
	DESCRIPTION
	"Static ruleset reconnects"
	INDEX { psmProvisionerOldStaticRulesetReconnectsLevelName }
	::={ psmProvisionerOldStaticRulesetReconnectsLevelTable 1 }

PsmProvisionerOldStaticRulesetReconnectsLevelEntry ::=
	SEQUENCE {
		psmProvisionerOldStaticRulesetReconnectsLevelName DisplayString,
		psmProvisionerOldStaticRulesetReconnectsLevelVal  Counter64,
		psmProvisionerOldStaticRulesetReconnectsLevelMom  CounterBasedGauge64,
		psmProvisionerOldStaticRulesetReconnectsLevelMax  CounterBasedGauge64
	}

psmProvisionerOldStaticRulesetReconnectsLevelName OBJECT-TYPE
	SYNTAX      DisplayString
	MAX-ACCESS  not-accessible
	STATUS      current
	DESCRIPTION
	"Static ruleset reconnects"
	::={ psmProvisionerOldStaticRulesetReconnectsLevelEntry 1}

psmProvisionerOldStaticRulesetReconnectsLevelVal OBJECT-TYPE
	SYNTAX     Counter64
	MAX-ACCESS read-only
	STATUS     current
	DESCRIPTION
	"Static ruleset reconnects"
	::={ psmProvisionerOldStaticRulesetReconnectsLevelEntry 2 }

psmProvisionerOldStaticRulesetReconnectsLevelMom OBJECT-TYPE
	SYNTAX     CounterBasedGauge64
	MAX-ACCESS read-only
	STATUS     current
	DESCRIPTION
	"Static ruleset reconnects"
	::={ psmProvisionerOldStaticRulesetReconnectsLevelEntry 3 }

psmProvisionerOldStaticRulesetReconnectsLevelMax OBJECT-TYPE
	SYNTAX     CounterBasedGauge64
	MAX-ACCESS read-only
	STATUS     current
	DESCRIPTION
	"Static ruleset reconnects"
	::={ psmProvisionerOldStaticRulesetReconnectsLevelEntry 4 }

psmProvisionerOldStaticRulesetRollbacks OBJECT IDENTIFIER ::= { psmProvisionerOld 13 }

psmProvisionerOldStaticRulesetRollbacksVal OBJECT-TYPE
	SYNTAX     Counter64
	MAX-ACCESS read-only
	STATUS     current
	DESCRIPTION "Static ruleset rollbacks"

	::={ psmProvisionerOldStaticRulesetRollbacks 1 }

psmProvisionerOldStaticRulesetRollbacksMom OBJECT-TYPE
	SYNTAX     CounterBasedGauge64
	MAX-ACCESS read-only
	STATUS     current
	DESCRIPTION "Static ruleset rollbacks"

	::={ psmProvisionerOldStaticRulesetRollbacks 2 }

psmProvisionerOldStaticRulesetRollbacksMax OBJECT-TYPE
	SYNTAX     CounterBasedGauge64
	MAX-ACCESS read-only
	STATUS     current
	DESCRIPTION "Static ruleset rollbacks"

	::={ psmProvisionerOldStaticRulesetRollbacks 3 }

psmProvisionerOldStaticRulesetRollbacksLevelTable OBJECT-TYPE
	SYNTAX     SEQUENCE OF PsmProvisionerOldStaticRulesetRollbacksLevelEntry
	MAX-ACCESS not-accessible
	STATUS     current
	DESCRIPTION
	"Static ruleset rollbacks"
	::={ psmProvisionerOldStaticRulesetRollbacks 4 }

psmProvisionerOldStaticRulesetRollbacksLevelEntry OBJECT-TYPE
	SYNTAX      PsmProvisionerOldStaticRulesetRollbacksLevelEntry
	MAX-ACCESS  not-accessible
	STATUS      current
	DESCRIPTION
	"Static ruleset rollbacks"
	INDEX { psmProvisionerOldStaticRulesetRollbacksLevelName }
	::={ psmProvisionerOldStaticRulesetRollbacksLevelTable 1 }

PsmProvisionerOldStaticRulesetRollbacksLevelEntry ::=
	SEQUENCE {
		psmProvisionerOldStaticRulesetRollbacksLevelName DisplayString,
		psmProvisionerOldStaticRulesetRollbacksLevelVal  Counter64,
		psmProvisionerOldStaticRulesetRollbacksLevelMom  CounterBasedGauge64,
		psmProvisionerOldStaticRulesetRollbacksLevelMax  CounterBasedGauge64
	}

psmProvisionerOldStaticRulesetRollbacksLevelName OBJECT-TYPE
	SYNTAX      DisplayString
	MAX-ACCESS  not-accessible
	STATUS      current
	DESCRIPTION
	"Static ruleset rollbacks"
	::={ psmProvisionerOldStaticRulesetRollbacksLevelEntry 1}

psmProvisionerOldStaticRulesetRollbacksLevelVal OBJECT-TYPE
	SYNTAX     Counter64
	MAX-ACCESS read-only
	STATUS     current
	DESCRIPTION
	"Static ruleset rollbacks"
	::={ psmProvisionerOldStaticRulesetRollbacksLevelEntry 2 }

psmProvisionerOldStaticRulesetRollbacksLevelMom OBJECT-TYPE
	SYNTAX     CounterBasedGauge64
	MAX-ACCESS read-only
	STATUS     current
	DESCRIPTION
	"Static ruleset rollbacks"
	::={ psmProvisionerOldStaticRulesetRollbacksLevelEntry 3 }

psmProvisionerOldStaticRulesetRollbacksLevelMax OBJECT-TYPE
	SYNTAX     CounterBasedGauge64
	MAX-ACCESS read-only
	STATUS     current
	DESCRIPTION
	"Static ruleset rollbacks"
	::={ psmProvisionerOldStaticRulesetRollbacksLevelEntry 4 }

psmProvisionerOldStaticRulesetState OBJECT IDENTIFIER ::= { psmProvisionerOld 14 }

psmProvisionerOldStaticRulesetStateVal OBJECT-TYPE
	SYNTAX     INTEGER {
		unconfigured(0),
		disconnected(1),
		requestRootNetobject(2),
		connecting(3),
		requestingSnapshot(4),
		connected(5),
		synchronizeInit(6),
		synchronizing(7),
		catchup(8),
		online(9)
	}
	MAX-ACCESS read-only
	STATUS     current
	DESCRIPTION "Static ruleset state"

	::={ psmProvisionerOldStaticRulesetState 1 }

psmProvisionerOldStaticRulesetStateLevelTable OBJECT-TYPE
	SYNTAX     SEQUENCE OF PsmProvisionerOldStaticRulesetStateLevelEntry
	MAX-ACCESS not-accessible
	STATUS     current
	DESCRIPTION
	"Static ruleset state"
	::={ psmProvisionerOldStaticRulesetState 4 }

psmProvisionerOldStaticRulesetStateLevelEntry OBJECT-TYPE
	SYNTAX      PsmProvisionerOldStaticRulesetStateLevelEntry
	MAX-ACCESS  not-accessible
	STATUS      current
	DESCRIPTION
	"Static ruleset state"
	INDEX { psmProvisionerOldStaticRulesetStateLevelName }
	::={ psmProvisionerOldStaticRulesetStateLevelTable 1 }

PsmProvisionerOldStaticRulesetStateLevelEntry ::=
	SEQUENCE {
		psmProvisionerOldStaticRulesetStateLevelName DisplayString,
		psmProvisionerOldStaticRulesetStateLevelVal  INTEGER
	}

psmProvisionerOldStaticRulesetStateLevelName OBJECT-TYPE
	SYNTAX      DisplayString
	MAX-ACCESS  not-accessible
	STATUS      current
	DESCRIPTION
	"Static ruleset state"
	::={ psmProvisionerOldStaticRulesetStateLevelEntry 1}

psmProvisionerOldStaticRulesetStateLevelVal OBJECT-TYPE
	SYNTAX     INTEGER {
		unconfigured(0),
		disconnected(1),
		requestRootNetobject(2),
		connecting(3),
		requestingSnapshot(4),
		connected(5),
		synchronizeInit(6),
		synchronizing(7),
		catchup(8),
		online(9)
	}
	MAX-ACCESS read-only
	STATUS     current
	DESCRIPTION
	"Static ruleset state"
	::={ psmProvisionerOldStaticRulesetStateLevelEntry 2 }

psmProvisionerOldDynamicRulesetUpdatesBacklog OBJECT IDENTIFIER ::= { psmProvisionerOld 15 }

psmProvisionerOldDynamicRulesetUpdatesBacklogVal OBJECT-TYPE
	SYNTAX     CounterBasedGauge64
	MAX-ACCESS read-only
	STATUS     current
	DESCRIPTION "Dynamic ruleset updates backlog"

	::={ psmProvisionerOldDynamicRulesetUpdatesBacklog 1 }

psmProvisionerOldDynamicRulesetUpdatesBacklogMax OBJECT-TYPE
	SYNTAX     CounterBasedGauge64
	MAX-ACCESS read-only
	STATUS     current
	DESCRIPTION "Dynamic ruleset updates backlog"

	::={ psmProvisionerOldDynamicRulesetUpdatesBacklog 3 }

psmProvisionerOldDynamicRulesetUpdatesBacklogLevelTable OBJECT-TYPE
	SYNTAX     SEQUENCE OF PsmProvisionerOldDynamicRulesetUpdatesBacklogLevelEntry
	MAX-ACCESS not-accessible
	STATUS     current
	DESCRIPTION
	"Dynamic ruleset updates backlog"
	::={ psmProvisionerOldDynamicRulesetUpdatesBacklog 4 }

psmProvisionerOldDynamicRulesetUpdatesBacklogLevelEntry OBJECT-TYPE
	SYNTAX      PsmProvisionerOldDynamicRulesetUpdatesBacklogLevelEntry
	MAX-ACCESS  not-accessible
	STATUS      current
	DESCRIPTION
	"Dynamic ruleset updates backlog"
	INDEX { psmProvisionerOldDynamicRulesetUpdatesBacklogLevelName }
	::={ psmProvisionerOldDynamicRulesetUpdatesBacklogLevelTable 1 }

PsmProvisionerOldDynamicRulesetUpdatesBacklogLevelEntry ::=
	SEQUENCE {
		psmProvisionerOldDynamicRulesetUpdatesBacklogLevelName DisplayString,
		psmProvisionerOldDynamicRulesetUpdatesBacklogLevelVal  CounterBasedGauge64,
		psmProvisionerOldDynamicRulesetUpdatesBacklogLevelMax  CounterBasedGauge64
	}

psmProvisionerOldDynamicRulesetUpdatesBacklogLevelName OBJECT-TYPE
	SYNTAX      DisplayString
	MAX-ACCESS  not-accessible
	STATUS      current
	DESCRIPTION
	"Dynamic ruleset updates backlog"
	::={ psmProvisionerOldDynamicRulesetUpdatesBacklogLevelEntry 1}

psmProvisionerOldDynamicRulesetUpdatesBacklogLevelVal OBJECT-TYPE
	SYNTAX     CounterBasedGauge64
	MAX-ACCESS read-only
	STATUS     current
	DESCRIPTION
	"Dynamic ruleset updates backlog"
	::={ psmProvisionerOldDynamicRulesetUpdatesBacklogLevelEntry 2 }

psmProvisionerOldDynamicRulesetUpdatesBacklogLevelMax OBJECT-TYPE
	SYNTAX     CounterBasedGauge64
	MAX-ACCESS read-only
	STATUS     current
	DESCRIPTION
	"Dynamic ruleset updates backlog"
	::={ psmProvisionerOldDynamicRulesetUpdatesBacklogLevelEntry 4 }

psmProvisionerOldDynamicRulesetCounterFlushes OBJECT IDENTIFIER ::= { psmProvisionerOld 16 }

psmProvisionerOldDynamicRulesetCounterFlushesVal OBJECT-TYPE
	SYNTAX     Counter64
	MAX-ACCESS read-only
	STATUS     current
	DESCRIPTION "Dynamic ruleset counter flushes"

	::={ psmProvisionerOldDynamicRulesetCounterFlushes 1 }

psmProvisionerOldDynamicRulesetCounterFlushesMom OBJECT-TYPE
	SYNTAX     CounterBasedGauge64
	MAX-ACCESS read-only
	STATUS     current
	DESCRIPTION "Dynamic ruleset counter flushes"

	::={ psmProvisionerOldDynamicRulesetCounterFlushes 2 }

psmProvisionerOldDynamicRulesetCounterFlushesMax OBJECT-TYPE
	SYNTAX     CounterBasedGauge64
	MAX-ACCESS read-only
	STATUS     current
	DESCRIPTION "Dynamic ruleset counter flushes"

	::={ psmProvisionerOldDynamicRulesetCounterFlushes 3 }

psmProvisionerOldDynamicRulesetCounterFlushesLevelTable OBJECT-TYPE
	SYNTAX     SEQUENCE OF PsmProvisionerOldDynamicRulesetCounterFlushesLevelEntry
	MAX-ACCESS not-accessible
	STATUS     current
	DESCRIPTION
	"Dynamic ruleset counter flushes"
	::={ psmProvisionerOldDynamicRulesetCounterFlushes 4 }

psmProvisionerOldDynamicRulesetCounterFlushesLevelEntry OBJECT-TYPE
	SYNTAX      PsmProvisionerOldDynamicRulesetCounterFlushesLevelEntry
	MAX-ACCESS  not-accessible
	STATUS      current
	DESCRIPTION
	"Dynamic ruleset counter flushes"
	INDEX { psmProvisionerOldDynamicRulesetCounterFlushesLevelName }
	::={ psmProvisionerOldDynamicRulesetCounterFlushesLevelTable 1 }

PsmProvisionerOldDynamicRulesetCounterFlushesLevelEntry ::=
	SEQUENCE {
		psmProvisionerOldDynamicRulesetCounterFlushesLevelName DisplayString,
		psmProvisionerOldDynamicRulesetCounterFlushesLevelVal  Counter64,
		psmProvisionerOldDynamicRulesetCounterFlushesLevelMom  CounterBasedGauge64,
		psmProvisionerOldDynamicRulesetCounterFlushesLevelMax  CounterBasedGauge64
	}

psmProvisionerOldDynamicRulesetCounterFlushesLevelName OBJECT-TYPE
	SYNTAX      DisplayString
	MAX-ACCESS  not-accessible
	STATUS      current
	DESCRIPTION
	"Dynamic ruleset counter flushes"
	::={ psmProvisionerOldDynamicRulesetCounterFlushesLevelEntry 1}

psmProvisionerOldDynamicRulesetCounterFlushesLevelVal OBJECT-TYPE
	SYNTAX     Counter64
	MAX-ACCESS read-only
	STATUS     current
	DESCRIPTION
	"Dynamic ruleset counter flushes"
	::={ psmProvisionerOldDynamicRulesetCounterFlushesLevelEntry 2 }

psmProvisionerOldDynamicRulesetCounterFlushesLevelMom OBJECT-TYPE
	SYNTAX     CounterBasedGauge64
	MAX-ACCESS read-only
	STATUS     current
	DESCRIPTION
	"Dynamic ruleset counter flushes"
	::={ psmProvisionerOldDynamicRulesetCounterFlushesLevelEntry 3 }

psmProvisionerOldDynamicRulesetCounterFlushesLevelMax OBJECT-TYPE
	SYNTAX     CounterBasedGauge64
	MAX-ACCESS read-only
	STATUS     current
	DESCRIPTION
	"Dynamic ruleset counter flushes"
	::={ psmProvisionerOldDynamicRulesetCounterFlushesLevelEntry 4 }

psmProvisionerOldDynamicRulesetCounterIssues OBJECT IDENTIFIER ::= { psmProvisionerOld 17 }

psmProvisionerOldDynamicRulesetCounterIssuesVal OBJECT-TYPE
	SYNTAX     Counter64
	MAX-ACCESS read-only
	STATUS     current
	DESCRIPTION "Dynamic ruleset counter issues"

	::={ psmProvisionerOldDynamicRulesetCounterIssues 1 }

psmProvisionerOldDynamicRulesetCounterIssuesMom OBJECT-TYPE
	SYNTAX     CounterBasedGauge64
	MAX-ACCESS read-only
	STATUS     current
	DESCRIPTION "Dynamic ruleset counter issues"

	::={ psmProvisionerOldDynamicRulesetCounterIssues 2 }

psmProvisionerOldDynamicRulesetCounterIssuesMax OBJECT-TYPE
	SYNTAX     CounterBasedGauge64
	MAX-ACCESS read-only
	STATUS     current
	DESCRIPTION "Dynamic ruleset counter issues"

	::={ psmProvisionerOldDynamicRulesetCounterIssues 3 }

psmProvisionerOldDynamicRulesetCounterIssuesLevelTable OBJECT-TYPE
	SYNTAX     SEQUENCE OF PsmProvisionerOldDynamicRulesetCounterIssuesLevelEntry
	MAX-ACCESS not-accessible
	STATUS     current
	DESCRIPTION
	"Dynamic ruleset counter issues"
	::={ psmProvisionerOldDynamicRulesetCounterIssues 4 }

psmProvisionerOldDynamicRulesetCounterIssuesLevelEntry OBJECT-TYPE
	SYNTAX      PsmProvisionerOldDynamicRulesetCounterIssuesLevelEntry
	MAX-ACCESS  not-accessible
	STATUS      current
	DESCRIPTION
	"Dynamic ruleset counter issues"
	INDEX { psmProvisionerOldDynamicRulesetCounterIssuesLevelName }
	::={ psmProvisionerOldDynamicRulesetCounterIssuesLevelTable 1 }

PsmProvisionerOldDynamicRulesetCounterIssuesLevelEntry ::=
	SEQUENCE {
		psmProvisionerOldDynamicRulesetCounterIssuesLevelName DisplayString,
		psmProvisionerOldDynamicRulesetCounterIssuesLevelVal  Counter64,
		psmProvisionerOldDynamicRulesetCounterIssuesLevelMom  CounterBasedGauge64,
		psmProvisionerOldDynamicRulesetCounterIssuesLevelMax  CounterBasedGauge64
	}

psmProvisionerOldDynamicRulesetCounterIssuesLevelName OBJECT-TYPE
	SYNTAX      DisplayString
	MAX-ACCESS  not-accessible
	STATUS      current
	DESCRIPTION
	"Dynamic ruleset counter issues"
	::={ psmProvisionerOldDynamicRulesetCounterIssuesLevelEntry 1}

psmProvisionerOldDynamicRulesetCounterIssuesLevelVal OBJECT-TYPE
	SYNTAX     Counter64
	MAX-ACCESS read-only
	STATUS     current
	DESCRIPTION
	"Dynamic ruleset counter issues"
	::={ psmProvisionerOldDynamicRulesetCounterIssuesLevelEntry 2 }

psmProvisionerOldDynamicRulesetCounterIssuesLevelMom OBJECT-TYPE
	SYNTAX     CounterBasedGauge64
	MAX-ACCESS read-only
	STATUS     current
	DESCRIPTION
	"Dynamic ruleset counter issues"
	::={ psmProvisionerOldDynamicRulesetCounterIssuesLevelEntry 3 }

psmProvisionerOldDynamicRulesetCounterIssuesLevelMax OBJECT-TYPE
	SYNTAX     CounterBasedGauge64
	MAX-ACCESS read-only
	STATUS     current
	DESCRIPTION
	"Dynamic ruleset counter issues"
	::={ psmProvisionerOldDynamicRulesetCounterIssuesLevelEntry 4 }

psmProvisionerOldDynamicRulesetCounterIssuesInvalidShapingObject OBJECT IDENTIFIER ::= { psmProvisionerOld 18 }

psmProvisionerOldDynamicRulesetCounterIssuesInvalidShapingObjectVal OBJECT-TYPE
	SYNTAX     Counter64
	MAX-ACCESS read-only
	STATUS     current
	DESCRIPTION "Dynamic ruleset counter issues: Invalid ShapingObject"

	::={ psmProvisionerOldDynamicRulesetCounterIssuesInvalidShapingObject 1 }

psmProvisionerOldDynamicRulesetCounterIssuesInvalidShapingObjectMom OBJECT-TYPE
	SYNTAX     CounterBasedGauge64
	MAX-ACCESS read-only
	STATUS     current
	DESCRIPTION "Dynamic ruleset counter issues: Invalid ShapingObject"

	::={ psmProvisionerOldDynamicRulesetCounterIssuesInvalidShapingObject 2 }

psmProvisionerOldDynamicRulesetCounterIssuesInvalidShapingObjectMax OBJECT-TYPE
	SYNTAX     CounterBasedGauge64
	MAX-ACCESS read-only
	STATUS     current
	DESCRIPTION "Dynamic ruleset counter issues: Invalid ShapingObject"

	::={ psmProvisionerOldDynamicRulesetCounterIssuesInvalidShapingObject 3 }

psmProvisionerOldDynamicRulesetCounterIssuesInvalidShapingObjectLevelTable OBJECT-TYPE
	SYNTAX     SEQUENCE OF PsmProvisionerOldDynamicRulesetCounterIssuesInvalidShapingObjectLevelEntry
	MAX-ACCESS not-accessible
	STATUS     current
	DESCRIPTION
	"Dynamic ruleset counter issues: Invalid ShapingObject"
	::={ psmProvisionerOldDynamicRulesetCounterIssuesInvalidShapingObject 4 }

psmProvisionerOldDynamicRulesetCounterIssuesInvalidShapingObjectLevelEntry OBJECT-TYPE
	SYNTAX      PsmProvisionerOldDynamicRulesetCounterIssuesInvalidShapingObjectLevelEntry
	MAX-ACCESS  not-accessible
	STATUS      current
	DESCRIPTION
	"Dynamic ruleset counter issues: Invalid ShapingObject"
	INDEX { psmProvisionerOldDynamicRulesetCounterIssuesInvalidShapingObjectLevelName }
	::={ psmProvisionerOldDynamicRulesetCounterIssuesInvalidShapingObjectLevelTable 1 }

PsmProvisionerOldDynamicRulesetCounterIssuesInvalidShapingObjectLevelEntry ::=
	SEQUENCE {
		psmProvisionerOldDynamicRulesetCounterIssuesInvalidShapingObjectLevelName DisplayString,
		psmProvisionerOldDynamicRulesetCounterIssuesInvalidShapingObjectLevelVal  Counter64,
		psmProvisionerOldDynamicRulesetCounterIssuesInvalidShapingObjectLevelMom  CounterBasedGauge64,
		psmProvisionerOldDynamicRulesetCounterIssuesInvalidShapingObjectLevelMax  CounterBasedGauge64
	}

psmProvisionerOldDynamicRulesetCounterIssuesInvalidShapingObjectLevelName OBJECT-TYPE
	SYNTAX      DisplayString
	MAX-ACCESS  not-accessible
	STATUS      current
	DESCRIPTION
	"Dynamic ruleset counter issues: Invalid ShapingObject"
	::={ psmProvisionerOldDynamicRulesetCounterIssuesInvalidShapingObjectLevelEntry 1}

psmProvisionerOldDynamicRulesetCounterIssuesInvalidShapingObjectLevelVal OBJECT-TYPE
	SYNTAX     Counter64
	MAX-ACCESS read-only
	STATUS     current
	DESCRIPTION
	"Dynamic ruleset counter issues: Invalid ShapingObject"
	::={ psmProvisionerOldDynamicRulesetCounterIssuesInvalidShapingObjectLevelEntry 2 }

psmProvisionerOldDynamicRulesetCounterIssuesInvalidShapingObjectLevelMom OBJECT-TYPE
	SYNTAX     CounterBasedGauge64
	MAX-ACCESS read-only
	STATUS     current
	DESCRIPTION
	"Dynamic ruleset counter issues: Invalid ShapingObject"
	::={ psmProvisionerOldDynamicRulesetCounterIssuesInvalidShapingObjectLevelEntry 3 }

psmProvisionerOldDynamicRulesetCounterIssuesInvalidShapingObjectLevelMax OBJECT-TYPE
	SYNTAX     CounterBasedGauge64
	MAX-ACCESS read-only
	STATUS     current
	DESCRIPTION
	"Dynamic ruleset counter issues: Invalid ShapingObject"
	::={ psmProvisionerOldDynamicRulesetCounterIssuesInvalidShapingObjectLevelEntry 4 }

psmProvisionerOldDynamicRulesetCounterIssuesInvalidSplitKey OBJECT IDENTIFIER ::= { psmProvisionerOld 19 }

psmProvisionerOldDynamicRulesetCounterIssuesInvalidSplitKeyVal OBJECT-TYPE
	SYNTAX     Counter64
	MAX-ACCESS read-only
	STATUS     current
	DESCRIPTION "Dynamic ruleset counter issues: Invalid split key"

	::={ psmProvisionerOldDynamicRulesetCounterIssuesInvalidSplitKey 1 }

psmProvisionerOldDynamicRulesetCounterIssuesInvalidSplitKeyMom OBJECT-TYPE
	SYNTAX     CounterBasedGauge64
	MAX-ACCESS read-only
	STATUS     current
	DESCRIPTION "Dynamic ruleset counter issues: Invalid split key"

	::={ psmProvisionerOldDynamicRulesetCounterIssuesInvalidSplitKey 2 }

psmProvisionerOldDynamicRulesetCounterIssuesInvalidSplitKeyMax OBJECT-TYPE
	SYNTAX     CounterBasedGauge64
	MAX-ACCESS read-only
	STATUS     current
	DESCRIPTION "Dynamic ruleset counter issues: Invalid split key"

	::={ psmProvisionerOldDynamicRulesetCounterIssuesInvalidSplitKey 3 }

psmProvisionerOldDynamicRulesetCounterIssuesInvalidSplitKeyLevelTable OBJECT-TYPE
	SYNTAX     SEQUENCE OF PsmProvisionerOldDynamicRulesetCounterIssuesInvalidSplitKeyLevelEntry
	MAX-ACCESS not-accessible
	STATUS     current
	DESCRIPTION
	"Dynamic ruleset counter issues: Invalid split key"
	::={ psmProvisionerOldDynamicRulesetCounterIssuesInvalidSplitKey 4 }

psmProvisionerOldDynamicRulesetCounterIssuesInvalidSplitKeyLevelEntry OBJECT-TYPE
	SYNTAX      PsmProvisionerOldDynamicRulesetCounterIssuesInvalidSplitKeyLevelEntry
	MAX-ACCESS  not-accessible
	STATUS      current
	DESCRIPTION
	"Dynamic ruleset counter issues: Invalid split key"
	INDEX { psmProvisionerOldDynamicRulesetCounterIssuesInvalidSplitKeyLevelName }
	::={ psmProvisionerOldDynamicRulesetCounterIssuesInvalidSplitKeyLevelTable 1 }

PsmProvisionerOldDynamicRulesetCounterIssuesInvalidSplitKeyLevelEntry ::=
	SEQUENCE {
		psmProvisionerOldDynamicRulesetCounterIssuesInvalidSplitKeyLevelName DisplayString,
		psmProvisionerOldDynamicRulesetCounterIssuesInvalidSplitKeyLevelVal  Counter64,
		psmProvisionerOldDynamicRulesetCounterIssuesInvalidSplitKeyLevelMom  CounterBasedGauge64,
		psmProvisionerOldDynamicRulesetCounterIssuesInvalidSplitKeyLevelMax  CounterBasedGauge64
	}

psmProvisionerOldDynamicRulesetCounterIssuesInvalidSplitKeyLevelName OBJECT-TYPE
	SYNTAX      DisplayString
	MAX-ACCESS  not-accessible
	STATUS      current
	DESCRIPTION
	"Dynamic ruleset counter issues: Invalid split key"
	::={ psmProvisionerOldDynamicRulesetCounterIssuesInvalidSplitKeyLevelEntry 1}

psmProvisionerOldDynamicRulesetCounterIssuesInvalidSplitKeyLevelVal OBJECT-TYPE
	SYNTAX     Counter64
	MAX-ACCESS read-only
	STATUS     current
	DESCRIPTION
	"Dynamic ruleset counter issues: Invalid split key"
	::={ psmProvisionerOldDynamicRulesetCounterIssuesInvalidSplitKeyLevelEntry 2 }

psmProvisionerOldDynamicRulesetCounterIssuesInvalidSplitKeyLevelMom OBJECT-TYPE
	SYNTAX     CounterBasedGauge64
	MAX-ACCESS read-only
	STATUS     current
	DESCRIPTION
	"Dynamic ruleset counter issues: Invalid split key"
	::={ psmProvisionerOldDynamicRulesetCounterIssuesInvalidSplitKeyLevelEntry 3 }

psmProvisionerOldDynamicRulesetCounterIssuesInvalidSplitKeyLevelMax OBJECT-TYPE
	SYNTAX     CounterBasedGauge64
	MAX-ACCESS read-only
	STATUS     current
	DESCRIPTION
	"Dynamic ruleset counter issues: Invalid split key"
	::={ psmProvisionerOldDynamicRulesetCounterIssuesInvalidSplitKeyLevelEntry 4 }

psmProvisionerOldDynamicRulesetCounterIssuesInvalidSplitKeyFormat OBJECT IDENTIFIER ::= { psmProvisionerOld 20 }

psmProvisionerOldDynamicRulesetCounterIssuesInvalidSplitKeyFormatVal OBJECT-TYPE
	SYNTAX     Counter64
	MAX-ACCESS read-only
	STATUS     current
	DESCRIPTION "Dynamic ruleset counter issues: Invalid split key format"

	::={ psmProvisionerOldDynamicRulesetCounterIssuesInvalidSplitKeyFormat 1 }

psmProvisionerOldDynamicRulesetCounterIssuesInvalidSplitKeyFormatMom OBJECT-TYPE
	SYNTAX     CounterBasedGauge64
	MAX-ACCESS read-only
	STATUS     current
	DESCRIPTION "Dynamic ruleset counter issues: Invalid split key format"

	::={ psmProvisionerOldDynamicRulesetCounterIssuesInvalidSplitKeyFormat 2 }

psmProvisionerOldDynamicRulesetCounterIssuesInvalidSplitKeyFormatMax OBJECT-TYPE
	SYNTAX     CounterBasedGauge64
	MAX-ACCESS read-only
	STATUS     current
	DESCRIPTION "Dynamic ruleset counter issues: Invalid split key format"

	::={ psmProvisionerOldDynamicRulesetCounterIssuesInvalidSplitKeyFormat 3 }

psmProvisionerOldDynamicRulesetCounterIssuesInvalidSplitKeyFormatLevelTable OBJECT-TYPE
	SYNTAX     SEQUENCE OF PsmProvisionerOldDynamicRulesetCounterIssuesInvalidSplitKeyFormatLevelEntry
	MAX-ACCESS not-accessible
	STATUS     current
	DESCRIPTION
	"Dynamic ruleset counter issues: Invalid split key format"
	::={ psmProvisionerOldDynamicRulesetCounterIssuesInvalidSplitKeyFormat 4 }

psmProvisionerOldDynamicRulesetCounterIssuesInvalidSplitKeyFormatLevelEntry OBJECT-TYPE
	SYNTAX      PsmProvisionerOldDynamicRulesetCounterIssuesInvalidSplitKeyFormatLevelEntry
	MAX-ACCESS  not-accessible
	STATUS      current
	DESCRIPTION
	"Dynamic ruleset counter issues: Invalid split key format"
	INDEX { psmProvisionerOldDynamicRulesetCounterIssuesInvalidSplitKeyFormatLevelName }
	::={ psmProvisionerOldDynamicRulesetCounterIssuesInvalidSplitKeyFormatLevelTable 1 }

PsmProvisionerOldDynamicRulesetCounterIssuesInvalidSplitKeyFormatLevelEntry ::=
	SEQUENCE {
		psmProvisionerOldDynamicRulesetCounterIssuesInvalidSplitKeyFormatLevelName DisplayString,
		psmProvisionerOldDynamicRulesetCounterIssuesInvalidSplitKeyFormatLevelVal  Counter64,
		psmProvisionerOldDynamicRulesetCounterIssuesInvalidSplitKeyFormatLevelMom  CounterBasedGauge64,
		psmProvisionerOldDynamicRulesetCounterIssuesInvalidSplitKeyFormatLevelMax  CounterBasedGauge64
	}

psmProvisionerOldDynamicRulesetCounterIssuesInvalidSplitKeyFormatLevelName OBJECT-TYPE
	SYNTAX      DisplayString
	MAX-ACCESS  not-accessible
	STATUS      current
	DESCRIPTION
	"Dynamic ruleset counter issues: Invalid split key format"
	::={ psmProvisionerOldDynamicRulesetCounterIssuesInvalidSplitKeyFormatLevelEntry 1}

psmProvisionerOldDynamicRulesetCounterIssuesInvalidSplitKeyFormatLevelVal OBJECT-TYPE
	SYNTAX     Counter64
	MAX-ACCESS read-only
	STATUS     current
	DESCRIPTION
	"Dynamic ruleset counter issues: Invalid split key format"
	::={ psmProvisionerOldDynamicRulesetCounterIssuesInvalidSplitKeyFormatLevelEntry 2 }

psmProvisionerOldDynamicRulesetCounterIssuesInvalidSplitKeyFormatLevelMom OBJECT-TYPE
	SYNTAX     CounterBasedGauge64
	MAX-ACCESS read-only
	STATUS     current
	DESCRIPTION
	"Dynamic ruleset counter issues: Invalid split key format"
	::={ psmProvisionerOldDynamicRulesetCounterIssuesInvalidSplitKeyFormatLevelEntry 3 }

psmProvisionerOldDynamicRulesetCounterIssuesInvalidSplitKeyFormatLevelMax OBJECT-TYPE
	SYNTAX     CounterBasedGauge64
	MAX-ACCESS read-only
	STATUS     current
	DESCRIPTION
	"Dynamic ruleset counter issues: Invalid split key format"
	::={ psmProvisionerOldDynamicRulesetCounterIssuesInvalidSplitKeyFormatLevelEntry 4 }

psmProvisionerOldDynamicRulesetCounterIssuesLastUpdateLost OBJECT IDENTIFIER ::= { psmProvisionerOld 21 }

psmProvisionerOldDynamicRulesetCounterIssuesLastUpdateLostVal OBJECT-TYPE
	SYNTAX     Counter64
	MAX-ACCESS read-only
	STATUS     current
	DESCRIPTION "Dynamic ruleset counter issues: Last update lost"

	::={ psmProvisionerOldDynamicRulesetCounterIssuesLastUpdateLost 1 }

psmProvisionerOldDynamicRulesetCounterIssuesLastUpdateLostMom OBJECT-TYPE
	SYNTAX     CounterBasedGauge64
	MAX-ACCESS read-only
	STATUS     current
	DESCRIPTION "Dynamic ruleset counter issues: Last update lost"

	::={ psmProvisionerOldDynamicRulesetCounterIssuesLastUpdateLost 2 }

psmProvisionerOldDynamicRulesetCounterIssuesLastUpdateLostMax OBJECT-TYPE
	SYNTAX     CounterBasedGauge64
	MAX-ACCESS read-only
	STATUS     current
	DESCRIPTION "Dynamic ruleset counter issues: Last update lost"

	::={ psmProvisionerOldDynamicRulesetCounterIssuesLastUpdateLost 3 }

psmProvisionerOldDynamicRulesetCounterIssuesLastUpdateLostLevelTable OBJECT-TYPE
	SYNTAX     SEQUENCE OF PsmProvisionerOldDynamicRulesetCounterIssuesLastUpdateLostLevelEntry
	MAX-ACCESS not-accessible
	STATUS     current
	DESCRIPTION
	"Dynamic ruleset counter issues: Last update lost"
	::={ psmProvisionerOldDynamicRulesetCounterIssuesLastUpdateLost 4 }

psmProvisionerOldDynamicRulesetCounterIssuesLastUpdateLostLevelEntry OBJECT-TYPE
	SYNTAX      PsmProvisionerOldDynamicRulesetCounterIssuesLastUpdateLostLevelEntry
	MAX-ACCESS  not-accessible
	STATUS      current
	DESCRIPTION
	"Dynamic ruleset counter issues: Last update lost"
	INDEX { psmProvisionerOldDynamicRulesetCounterIssuesLastUpdateLostLevelName }
	::={ psmProvisionerOldDynamicRulesetCounterIssuesLastUpdateLostLevelTable 1 }

PsmProvisionerOldDynamicRulesetCounterIssuesLastUpdateLostLevelEntry ::=
	SEQUENCE {
		psmProvisionerOldDynamicRulesetCounterIssuesLastUpdateLostLevelName DisplayString,
		psmProvisionerOldDynamicRulesetCounterIssuesLastUpdateLostLevelVal  Counter64,
		psmProvisionerOldDynamicRulesetCounterIssuesLastUpdateLostLevelMom  CounterBasedGauge64,
		psmProvisionerOldDynamicRulesetCounterIssuesLastUpdateLostLevelMax  CounterBasedGauge64
	}

psmProvisionerOldDynamicRulesetCounterIssuesLastUpdateLostLevelName OBJECT-TYPE
	SYNTAX      DisplayString
	MAX-ACCESS  not-accessible
	STATUS      current
	DESCRIPTION
	"Dynamic ruleset counter issues: Last update lost"
	::={ psmProvisionerOldDynamicRulesetCounterIssuesLastUpdateLostLevelEntry 1}

psmProvisionerOldDynamicRulesetCounterIssuesLastUpdateLostLevelVal OBJECT-TYPE
	SYNTAX     Counter64
	MAX-ACCESS read-only
	STATUS     current
	DESCRIPTION
	"Dynamic ruleset counter issues: Last update lost"
	::={ psmProvisionerOldDynamicRulesetCounterIssuesLastUpdateLostLevelEntry 2 }

psmProvisionerOldDynamicRulesetCounterIssuesLastUpdateLostLevelMom OBJECT-TYPE
	SYNTAX     CounterBasedGauge64
	MAX-ACCESS read-only
	STATUS     current
	DESCRIPTION
	"Dynamic ruleset counter issues: Last update lost"
	::={ psmProvisionerOldDynamicRulesetCounterIssuesLastUpdateLostLevelEntry 3 }

psmProvisionerOldDynamicRulesetCounterIssuesLastUpdateLostLevelMax OBJECT-TYPE
	SYNTAX     CounterBasedGauge64
	MAX-ACCESS read-only
	STATUS     current
	DESCRIPTION
	"Dynamic ruleset counter issues: Last update lost"
	::={ psmProvisionerOldDynamicRulesetCounterIssuesLastUpdateLostLevelEntry 4 }

psmProvisionerOldDynamicRulesetCounterIssuesNotSplitBySubscriber OBJECT IDENTIFIER ::= { psmProvisionerOld 22 }

psmProvisionerOldDynamicRulesetCounterIssuesNotSplitBySubscriberVal OBJECT-TYPE
	SYNTAX     Counter64
	MAX-ACCESS read-only
	STATUS     current
	DESCRIPTION "Dynamic ruleset counter issues: Not split by subscriber"

	::={ psmProvisionerOldDynamicRulesetCounterIssuesNotSplitBySubscriber 1 }

psmProvisionerOldDynamicRulesetCounterIssuesNotSplitBySubscriberMom OBJECT-TYPE
	SYNTAX     CounterBasedGauge64
	MAX-ACCESS read-only
	STATUS     current
	DESCRIPTION "Dynamic ruleset counter issues: Not split by subscriber"

	::={ psmProvisionerOldDynamicRulesetCounterIssuesNotSplitBySubscriber 2 }

psmProvisionerOldDynamicRulesetCounterIssuesNotSplitBySubscriberMax OBJECT-TYPE
	SYNTAX     CounterBasedGauge64
	MAX-ACCESS read-only
	STATUS     current
	DESCRIPTION "Dynamic ruleset counter issues: Not split by subscriber"

	::={ psmProvisionerOldDynamicRulesetCounterIssuesNotSplitBySubscriber 3 }

psmProvisionerOldDynamicRulesetCounterIssuesNotSplitBySubscriberLevelTable OBJECT-TYPE
	SYNTAX     SEQUENCE OF PsmProvisionerOldDynamicRulesetCounterIssuesNotSplitBySubscriberLevelEntry
	MAX-ACCESS not-accessible
	STATUS     current
	DESCRIPTION
	"Dynamic ruleset counter issues: Not split by subscriber"
	::={ psmProvisionerOldDynamicRulesetCounterIssuesNotSplitBySubscriber 4 }

psmProvisionerOldDynamicRulesetCounterIssuesNotSplitBySubscriberLevelEntry OBJECT-TYPE
	SYNTAX      PsmProvisionerOldDynamicRulesetCounterIssuesNotSplitBySubscriberLevelEntry
	MAX-ACCESS  not-accessible
	STATUS      current
	DESCRIPTION
	"Dynamic ruleset counter issues: Not split by subscriber"
	INDEX { psmProvisionerOldDynamicRulesetCounterIssuesNotSplitBySubscriberLevelName }
	::={ psmProvisionerOldDynamicRulesetCounterIssuesNotSplitBySubscriberLevelTable 1 }

PsmProvisionerOldDynamicRulesetCounterIssuesNotSplitBySubscriberLevelEntry ::=
	SEQUENCE {
		psmProvisionerOldDynamicRulesetCounterIssuesNotSplitBySubscriberLevelName DisplayString,
		psmProvisionerOldDynamicRulesetCounterIssuesNotSplitBySubscriberLevelVal  Counter64,
		psmProvisionerOldDynamicRulesetCounterIssuesNotSplitBySubscriberLevelMom  CounterBasedGauge64,
		psmProvisionerOldDynamicRulesetCounterIssuesNotSplitBySubscriberLevelMax  CounterBasedGauge64
	}

psmProvisionerOldDynamicRulesetCounterIssuesNotSplitBySubscriberLevelName OBJECT-TYPE
	SYNTAX      DisplayString
	MAX-ACCESS  not-accessible
	STATUS      current
	DESCRIPTION
	"Dynamic ruleset counter issues: Not split by subscriber"
	::={ psmProvisionerOldDynamicRulesetCounterIssuesNotSplitBySubscriberLevelEntry 1}

psmProvisionerOldDynamicRulesetCounterIssuesNotSplitBySubscriberLevelVal OBJECT-TYPE
	SYNTAX     Counter64
	MAX-ACCESS read-only
	STATUS     current
	DESCRIPTION
	"Dynamic ruleset counter issues: Not split by subscriber"
	::={ psmProvisionerOldDynamicRulesetCounterIssuesNotSplitBySubscriberLevelEntry 2 }

psmProvisionerOldDynamicRulesetCounterIssuesNotSplitBySubscriberLevelMom OBJECT-TYPE
	SYNTAX     CounterBasedGauge64
	MAX-ACCESS read-only
	STATUS     current
	DESCRIPTION
	"Dynamic ruleset counter issues: Not split by subscriber"
	::={ psmProvisionerOldDynamicRulesetCounterIssuesNotSplitBySubscriberLevelEntry 3 }

psmProvisionerOldDynamicRulesetCounterIssuesNotSplitBySubscriberLevelMax OBJECT-TYPE
	SYNTAX     CounterBasedGauge64
	MAX-ACCESS read-only
	STATUS     current
	DESCRIPTION
	"Dynamic ruleset counter issues: Not split by subscriber"
	::={ psmProvisionerOldDynamicRulesetCounterIssuesNotSplitBySubscriberLevelEntry 4 }

psmProvisionerOldDynamicRulesetCounterIssuesSplitKeyMismatch OBJECT IDENTIFIER ::= { psmProvisionerOld 23 }

psmProvisionerOldDynamicRulesetCounterIssuesSplitKeyMismatchVal OBJECT-TYPE
	SYNTAX     Counter64
	MAX-ACCESS read-only
	STATUS     current
	DESCRIPTION "Dynamic ruleset counter issues: Split key mismatch"

	::={ psmProvisionerOldDynamicRulesetCounterIssuesSplitKeyMismatch 1 }

psmProvisionerOldDynamicRulesetCounterIssuesSplitKeyMismatchMom OBJECT-TYPE
	SYNTAX     CounterBasedGauge64
	MAX-ACCESS read-only
	STATUS     current
	DESCRIPTION "Dynamic ruleset counter issues: Split key mismatch"

	::={ psmProvisionerOldDynamicRulesetCounterIssuesSplitKeyMismatch 2 }

psmProvisionerOldDynamicRulesetCounterIssuesSplitKeyMismatchMax OBJECT-TYPE
	SYNTAX     CounterBasedGauge64
	MAX-ACCESS read-only
	STATUS     current
	DESCRIPTION "Dynamic ruleset counter issues: Split key mismatch"

	::={ psmProvisionerOldDynamicRulesetCounterIssuesSplitKeyMismatch 3 }

psmProvisionerOldDynamicRulesetCounterIssuesSplitKeyMismatchLevelTable OBJECT-TYPE
	SYNTAX     SEQUENCE OF PsmProvisionerOldDynamicRulesetCounterIssuesSplitKeyMismatchLevelEntry
	MAX-ACCESS not-accessible
	STATUS     current
	DESCRIPTION
	"Dynamic ruleset counter issues: Split key mismatch"
	::={ psmProvisionerOldDynamicRulesetCounterIssuesSplitKeyMismatch 4 }

psmProvisionerOldDynamicRulesetCounterIssuesSplitKeyMismatchLevelEntry OBJECT-TYPE
	SYNTAX      PsmProvisionerOldDynamicRulesetCounterIssuesSplitKeyMismatchLevelEntry
	MAX-ACCESS  not-accessible
	STATUS      current
	DESCRIPTION
	"Dynamic ruleset counter issues: Split key mismatch"
	INDEX { psmProvisionerOldDynamicRulesetCounterIssuesSplitKeyMismatchLevelName }
	::={ psmProvisionerOldDynamicRulesetCounterIssuesSplitKeyMismatchLevelTable 1 }

PsmProvisionerOldDynamicRulesetCounterIssuesSplitKeyMismatchLevelEntry ::=
	SEQUENCE {
		psmProvisionerOldDynamicRulesetCounterIssuesSplitKeyMismatchLevelName DisplayString,
		psmProvisionerOldDynamicRulesetCounterIssuesSplitKeyMismatchLevelVal  Counter64,
		psmProvisionerOldDynamicRulesetCounterIssuesSplitKeyMismatchLevelMom  CounterBasedGauge64,
		psmProvisionerOldDynamicRulesetCounterIssuesSplitKeyMismatchLevelMax  CounterBasedGauge64
	}

psmProvisionerOldDynamicRulesetCounterIssuesSplitKeyMismatchLevelName OBJECT-TYPE
	SYNTAX      DisplayString
	MAX-ACCESS  not-accessible
	STATUS      current
	DESCRIPTION
	"Dynamic ruleset counter issues: Split key mismatch"
	::={ psmProvisionerOldDynamicRulesetCounterIssuesSplitKeyMismatchLevelEntry 1}

psmProvisionerOldDynamicRulesetCounterIssuesSplitKeyMismatchLevelVal OBJECT-TYPE
	SYNTAX     Counter64
	MAX-ACCESS read-only
	STATUS     current
	DESCRIPTION
	"Dynamic ruleset counter issues: Split key mismatch"
	::={ psmProvisionerOldDynamicRulesetCounterIssuesSplitKeyMismatchLevelEntry 2 }

psmProvisionerOldDynamicRulesetCounterIssuesSplitKeyMismatchLevelMom OBJECT-TYPE
	SYNTAX     CounterBasedGauge64
	MAX-ACCESS read-only
	STATUS     current
	DESCRIPTION
	"Dynamic ruleset counter issues: Split key mismatch"
	::={ psmProvisionerOldDynamicRulesetCounterIssuesSplitKeyMismatchLevelEntry 3 }

psmProvisionerOldDynamicRulesetCounterIssuesSplitKeyMismatchLevelMax OBJECT-TYPE
	SYNTAX     CounterBasedGauge64
	MAX-ACCESS read-only
	STATUS     current
	DESCRIPTION
	"Dynamic ruleset counter issues: Split key mismatch"
	::={ psmProvisionerOldDynamicRulesetCounterIssuesSplitKeyMismatchLevelEntry 4 }

psmProvisionerOldDynamicRulesetCounterIssuesUpdateOutOfBounds OBJECT IDENTIFIER ::= { psmProvisionerOld 24 }

psmProvisionerOldDynamicRulesetCounterIssuesUpdateOutOfBoundsVal OBJECT-TYPE
	SYNTAX     Counter64
	MAX-ACCESS read-only
	STATUS     current
	DESCRIPTION "Dynamic ruleset counter issues: Update out of bounds"

	::={ psmProvisionerOldDynamicRulesetCounterIssuesUpdateOutOfBounds 1 }

psmProvisionerOldDynamicRulesetCounterIssuesUpdateOutOfBoundsMom OBJECT-TYPE
	SYNTAX     CounterBasedGauge64
	MAX-ACCESS read-only
	STATUS     current
	DESCRIPTION "Dynamic ruleset counter issues: Update out of bounds"

	::={ psmProvisionerOldDynamicRulesetCounterIssuesUpdateOutOfBounds 2 }

psmProvisionerOldDynamicRulesetCounterIssuesUpdateOutOfBoundsMax OBJECT-TYPE
	SYNTAX     CounterBasedGauge64
	MAX-ACCESS read-only
	STATUS     current
	DESCRIPTION "Dynamic ruleset counter issues: Update out of bounds"

	::={ psmProvisionerOldDynamicRulesetCounterIssuesUpdateOutOfBounds 3 }

psmProvisionerOldDynamicRulesetCounterIssuesUpdateOutOfBoundsLevelTable OBJECT-TYPE
	SYNTAX     SEQUENCE OF PsmProvisionerOldDynamicRulesetCounterIssuesUpdateOutOfBoundsLevelEntry
	MAX-ACCESS not-accessible
	STATUS     current
	DESCRIPTION
	"Dynamic ruleset counter issues: Update out of bounds"
	::={ psmProvisionerOldDynamicRulesetCounterIssuesUpdateOutOfBounds 4 }

psmProvisionerOldDynamicRulesetCounterIssuesUpdateOutOfBoundsLevelEntry OBJECT-TYPE
	SYNTAX      PsmProvisionerOldDynamicRulesetCounterIssuesUpdateOutOfBoundsLevelEntry
	MAX-ACCESS  not-accessible
	STATUS      current
	DESCRIPTION
	"Dynamic ruleset counter issues: Update out of bounds"
	INDEX { psmProvisionerOldDynamicRulesetCounterIssuesUpdateOutOfBoundsLevelName }
	::={ psmProvisionerOldDynamicRulesetCounterIssuesUpdateOutOfBoundsLevelTable 1 }

PsmProvisionerOldDynamicRulesetCounterIssuesUpdateOutOfBoundsLevelEntry ::=
	SEQUENCE {
		psmProvisionerOldDynamicRulesetCounterIssuesUpdateOutOfBoundsLevelName DisplayString,
		psmProvisionerOldDynamicRulesetCounterIssuesUpdateOutOfBoundsLevelVal  Counter64,
		psmProvisionerOldDynamicRulesetCounterIssuesUpdateOutOfBoundsLevelMom  CounterBasedGauge64,
		psmProvisionerOldDynamicRulesetCounterIssuesUpdateOutOfBoundsLevelMax  CounterBasedGauge64
	}

psmProvisionerOldDynamicRulesetCounterIssuesUpdateOutOfBoundsLevelName OBJECT-TYPE
	SYNTAX      DisplayString
	MAX-ACCESS  not-accessible
	STATUS      current
	DESCRIPTION
	"Dynamic ruleset counter issues: Update out of bounds"
	::={ psmProvisionerOldDynamicRulesetCounterIssuesUpdateOutOfBoundsLevelEntry 1}

psmProvisionerOldDynamicRulesetCounterIssuesUpdateOutOfBoundsLevelVal OBJECT-TYPE
	SYNTAX     Counter64
	MAX-ACCESS read-only
	STATUS     current
	DESCRIPTION
	"Dynamic ruleset counter issues: Update out of bounds"
	::={ psmProvisionerOldDynamicRulesetCounterIssuesUpdateOutOfBoundsLevelEntry 2 }

psmProvisionerOldDynamicRulesetCounterIssuesUpdateOutOfBoundsLevelMom OBJECT-TYPE
	SYNTAX     CounterBasedGauge64
	MAX-ACCESS read-only
	STATUS     current
	DESCRIPTION
	"Dynamic ruleset counter issues: Update out of bounds"
	::={ psmProvisionerOldDynamicRulesetCounterIssuesUpdateOutOfBoundsLevelEntry 3 }

psmProvisionerOldDynamicRulesetCounterIssuesUpdateOutOfBoundsLevelMax OBJECT-TYPE
	SYNTAX     CounterBasedGauge64
	MAX-ACCESS read-only
	STATUS     current
	DESCRIPTION
	"Dynamic ruleset counter issues: Update out of bounds"
	::={ psmProvisionerOldDynamicRulesetCounterIssuesUpdateOutOfBoundsLevelEntry 4 }

psmProvisionerOldDynamicRulesetCounterIssuesUpdatesBeforeInitialized OBJECT IDENTIFIER ::= { psmProvisionerOld 25 }

psmProvisionerOldDynamicRulesetCounterIssuesUpdatesBeforeInitializedVal OBJECT-TYPE
	SYNTAX     Counter64
	MAX-ACCESS read-only
	STATUS     current
	DESCRIPTION "Dynamic ruleset counter issues: Updates before initialized"

	::={ psmProvisionerOldDynamicRulesetCounterIssuesUpdatesBeforeInitialized 1 }

psmProvisionerOldDynamicRulesetCounterIssuesUpdatesBeforeInitializedMom OBJECT-TYPE
	SYNTAX     CounterBasedGauge64
	MAX-ACCESS read-only
	STATUS     current
	DESCRIPTION "Dynamic ruleset counter issues: Updates before initialized"

	::={ psmProvisionerOldDynamicRulesetCounterIssuesUpdatesBeforeInitialized 2 }

psmProvisionerOldDynamicRulesetCounterIssuesUpdatesBeforeInitializedMax OBJECT-TYPE
	SYNTAX     CounterBasedGauge64
	MAX-ACCESS read-only
	STATUS     current
	DESCRIPTION "Dynamic ruleset counter issues: Updates before initialized"

	::={ psmProvisionerOldDynamicRulesetCounterIssuesUpdatesBeforeInitialized 3 }

psmProvisionerOldDynamicRulesetCounterIssuesUpdatesBeforeInitializedLevelTable OBJECT-TYPE
	SYNTAX     SEQUENCE OF PsmProvisionerOldDynamicRulesetCounterIssuesUpdatesBeforeInitializedLevelEntry
	MAX-ACCESS not-accessible
	STATUS     current
	DESCRIPTION
	"Dynamic ruleset counter issues: Updates before initialized"
	::={ psmProvisionerOldDynamicRulesetCounterIssuesUpdatesBeforeInitialized 4 }

psmProvisionerOldDynamicRulesetCounterIssuesUpdatesBeforeInitializedLevelEntry OBJECT-TYPE
	SYNTAX      PsmProvisionerOldDynamicRulesetCounterIssuesUpdatesBeforeInitializedLevelEntry
	MAX-ACCESS  not-accessible
	STATUS      current
	DESCRIPTION
	"Dynamic ruleset counter issues: Updates before initialized"
	INDEX { psmProvisionerOldDynamicRulesetCounterIssuesUpdatesBeforeInitializedLevelName }
	::={ psmProvisionerOldDynamicRulesetCounterIssuesUpdatesBeforeInitializedLevelTable 1 }

PsmProvisionerOldDynamicRulesetCounterIssuesUpdatesBeforeInitializedLevelEntry ::=
	SEQUENCE {
		psmProvisionerOldDynamicRulesetCounterIssuesUpdatesBeforeInitializedLevelName DisplayString,
		psmProvisionerOldDynamicRulesetCounterIssuesUpdatesBeforeInitializedLevelVal  Counter64,
		psmProvisionerOldDynamicRulesetCounterIssuesUpdatesBeforeInitializedLevelMom  CounterBasedGauge64,
		psmProvisionerOldDynamicRulesetCounterIssuesUpdatesBeforeInitializedLevelMax  CounterBasedGauge64
	}

psmProvisionerOldDynamicRulesetCounterIssuesUpdatesBeforeInitializedLevelName OBJECT-TYPE
	SYNTAX      DisplayString
	MAX-ACCESS  not-accessible
	STATUS      current
	DESCRIPTION
	"Dynamic ruleset counter issues: Updates before initialized"
	::={ psmProvisionerOldDynamicRulesetCounterIssuesUpdatesBeforeInitializedLevelEntry 1}

psmProvisionerOldDynamicRulesetCounterIssuesUpdatesBeforeInitializedLevelVal OBJECT-TYPE
	SYNTAX     Counter64
	MAX-ACCESS read-only
	STATUS     current
	DESCRIPTION
	"Dynamic ruleset counter issues: Updates before initialized"
	::={ psmProvisionerOldDynamicRulesetCounterIssuesUpdatesBeforeInitializedLevelEntry 2 }

psmProvisionerOldDynamicRulesetCounterIssuesUpdatesBeforeInitializedLevelMom OBJECT-TYPE
	SYNTAX     CounterBasedGauge64
	MAX-ACCESS read-only
	STATUS     current
	DESCRIPTION
	"Dynamic ruleset counter issues: Updates before initialized"
	::={ psmProvisionerOldDynamicRulesetCounterIssuesUpdatesBeforeInitializedLevelEntry 3 }

psmProvisionerOldDynamicRulesetCounterIssuesUpdatesBeforeInitializedLevelMax OBJECT-TYPE
	SYNTAX     CounterBasedGauge64
	MAX-ACCESS read-only
	STATUS     current
	DESCRIPTION
	"Dynamic ruleset counter issues: Updates before initialized"
	::={ psmProvisionerOldDynamicRulesetCounterIssuesUpdatesBeforeInitializedLevelEntry 4 }

psmProvisionerOldDynamicRulesetCounters OBJECT IDENTIFIER ::= { psmProvisionerOld 26 }

psmProvisionerOldDynamicRulesetCountersVal OBJECT-TYPE
	SYNTAX     Counter64
	MAX-ACCESS read-only
	STATUS     current
	DESCRIPTION "Dynamic ruleset counters"

	::={ psmProvisionerOldDynamicRulesetCounters 1 }

psmProvisionerOldDynamicRulesetCountersMom OBJECT-TYPE
	SYNTAX     CounterBasedGauge64
	MAX-ACCESS read-only
	STATUS     current
	DESCRIPTION "Dynamic ruleset counters"

	::={ psmProvisionerOldDynamicRulesetCounters 2 }

psmProvisionerOldDynamicRulesetCountersMax OBJECT-TYPE
	SYNTAX     CounterBasedGauge64
	MAX-ACCESS read-only
	STATUS     current
	DESCRIPTION "Dynamic ruleset counters"

	::={ psmProvisionerOldDynamicRulesetCounters 3 }

psmProvisionerOldDynamicRulesetCountersLevelTable OBJECT-TYPE
	SYNTAX     SEQUENCE OF PsmProvisionerOldDynamicRulesetCountersLevelEntry
	MAX-ACCESS not-accessible
	STATUS     current
	DESCRIPTION
	"Dynamic ruleset counters"
	::={ psmProvisionerOldDynamicRulesetCounters 4 }

psmProvisionerOldDynamicRulesetCountersLevelEntry OBJECT-TYPE
	SYNTAX      PsmProvisionerOldDynamicRulesetCountersLevelEntry
	MAX-ACCESS  not-accessible
	STATUS      current
	DESCRIPTION
	"Dynamic ruleset counters"
	INDEX { psmProvisionerOldDynamicRulesetCountersLevelName }
	::={ psmProvisionerOldDynamicRulesetCountersLevelTable 1 }

PsmProvisionerOldDynamicRulesetCountersLevelEntry ::=
	SEQUENCE {
		psmProvisionerOldDynamicRulesetCountersLevelName DisplayString,
		psmProvisionerOldDynamicRulesetCountersLevelVal  Counter64,
		psmProvisionerOldDynamicRulesetCountersLevelMom  CounterBasedGauge64,
		psmProvisionerOldDynamicRulesetCountersLevelMax  CounterBasedGauge64
	}

psmProvisionerOldDynamicRulesetCountersLevelName OBJECT-TYPE
	SYNTAX      DisplayString
	MAX-ACCESS  not-accessible
	STATUS      current
	DESCRIPTION
	"Dynamic ruleset counters"
	::={ psmProvisionerOldDynamicRulesetCountersLevelEntry 1}

psmProvisionerOldDynamicRulesetCountersLevelVal OBJECT-TYPE
	SYNTAX     Counter64
	MAX-ACCESS read-only
	STATUS     current
	DESCRIPTION
	"Dynamic ruleset counters"
	::={ psmProvisionerOldDynamicRulesetCountersLevelEntry 2 }

psmProvisionerOldDynamicRulesetCountersLevelMom OBJECT-TYPE
	SYNTAX     CounterBasedGauge64
	MAX-ACCESS read-only
	STATUS     current
	DESCRIPTION
	"Dynamic ruleset counters"
	::={ psmProvisionerOldDynamicRulesetCountersLevelEntry 3 }

psmProvisionerOldDynamicRulesetCountersLevelMax OBJECT-TYPE
	SYNTAX     CounterBasedGauge64
	MAX-ACCESS read-only
	STATUS     current
	DESCRIPTION
	"Dynamic ruleset counters"
	::={ psmProvisionerOldDynamicRulesetCountersLevelEntry 4 }

psmProvisionerOldDynamicRulesetUpdates OBJECT IDENTIFIER ::= { psmProvisionerOld 27 }

psmProvisionerOldDynamicRulesetUpdatesVal OBJECT-TYPE
	SYNTAX     Counter64
	MAX-ACCESS read-only
	STATUS     current
	DESCRIPTION "Dynamic ruleset updates"

	::={ psmProvisionerOldDynamicRulesetUpdates 1 }

psmProvisionerOldDynamicRulesetUpdatesMom OBJECT-TYPE
	SYNTAX     CounterBasedGauge64
	MAX-ACCESS read-only
	STATUS     current
	DESCRIPTION "Dynamic ruleset updates"

	::={ psmProvisionerOldDynamicRulesetUpdates 2 }

psmProvisionerOldDynamicRulesetUpdatesMax OBJECT-TYPE
	SYNTAX     CounterBasedGauge64
	MAX-ACCESS read-only
	STATUS     current
	DESCRIPTION "Dynamic ruleset updates"

	::={ psmProvisionerOldDynamicRulesetUpdates 3 }

psmProvisionerOldDynamicRulesetUpdatesLevelTable OBJECT-TYPE
	SYNTAX     SEQUENCE OF PsmProvisionerOldDynamicRulesetUpdatesLevelEntry
	MAX-ACCESS not-accessible
	STATUS     current
	DESCRIPTION
	"Dynamic ruleset updates"
	::={ psmProvisionerOldDynamicRulesetUpdates 4 }

psmProvisionerOldDynamicRulesetUpdatesLevelEntry OBJECT-TYPE
	SYNTAX      PsmProvisionerOldDynamicRulesetUpdatesLevelEntry
	MAX-ACCESS  not-accessible
	STATUS      current
	DESCRIPTION
	"Dynamic ruleset updates"
	INDEX { psmProvisionerOldDynamicRulesetUpdatesLevelName }
	::={ psmProvisionerOldDynamicRulesetUpdatesLevelTable 1 }

PsmProvisionerOldDynamicRulesetUpdatesLevelEntry ::=
	SEQUENCE {
		psmProvisionerOldDynamicRulesetUpdatesLevelName DisplayString,
		psmProvisionerOldDynamicRulesetUpdatesLevelVal  Counter64,
		psmProvisionerOldDynamicRulesetUpdatesLevelMom  CounterBasedGauge64,
		psmProvisionerOldDynamicRulesetUpdatesLevelMax  CounterBasedGauge64
	}

psmProvisionerOldDynamicRulesetUpdatesLevelName OBJECT-TYPE
	SYNTAX      DisplayString
	MAX-ACCESS  not-accessible
	STATUS      current
	DESCRIPTION
	"Dynamic ruleset updates"
	::={ psmProvisionerOldDynamicRulesetUpdatesLevelEntry 1}

psmProvisionerOldDynamicRulesetUpdatesLevelVal OBJECT-TYPE
	SYNTAX     Counter64
	MAX-ACCESS read-only
	STATUS     current
	DESCRIPTION
	"Dynamic ruleset updates"
	::={ psmProvisionerOldDynamicRulesetUpdatesLevelEntry 2 }

psmProvisionerOldDynamicRulesetUpdatesLevelMom OBJECT-TYPE
	SYNTAX     CounterBasedGauge64
	MAX-ACCESS read-only
	STATUS     current
	DESCRIPTION
	"Dynamic ruleset updates"
	::={ psmProvisionerOldDynamicRulesetUpdatesLevelEntry 3 }

psmProvisionerOldDynamicRulesetUpdatesLevelMax OBJECT-TYPE
	SYNTAX     CounterBasedGauge64
	MAX-ACCESS read-only
	STATUS     current
	DESCRIPTION
	"Dynamic ruleset updates"
	::={ psmProvisionerOldDynamicRulesetUpdatesLevelEntry 4 }

psmProvisionerOldDynamicRulesetEnabled OBJECT IDENTIFIER ::= { psmProvisionerOld 28 }

psmProvisionerOldDynamicRulesetEnabledVal OBJECT-TYPE
	SYNTAX     INTEGER {
		false(0),
		true(1)
	}
	MAX-ACCESS read-only
	STATUS     current
	DESCRIPTION "Dynamic ruleset enabled"

	::={ psmProvisionerOldDynamicRulesetEnabled 1 }

psmProvisionerOldDynamicRulesetEnabledLevelTable OBJECT-TYPE
	SYNTAX     SEQUENCE OF PsmProvisionerOldDynamicRulesetEnabledLevelEntry
	MAX-ACCESS not-accessible
	STATUS     current
	DESCRIPTION
	"Dynamic ruleset enabled"
	::={ psmProvisionerOldDynamicRulesetEnabled 4 }

psmProvisionerOldDynamicRulesetEnabledLevelEntry OBJECT-TYPE
	SYNTAX      PsmProvisionerOldDynamicRulesetEnabledLevelEntry
	MAX-ACCESS  not-accessible
	STATUS      current
	DESCRIPTION
	"Dynamic ruleset enabled"
	INDEX { psmProvisionerOldDynamicRulesetEnabledLevelName }
	::={ psmProvisionerOldDynamicRulesetEnabledLevelTable 1 }

PsmProvisionerOldDynamicRulesetEnabledLevelEntry ::=
	SEQUENCE {
		psmProvisionerOldDynamicRulesetEnabledLevelName DisplayString,
		psmProvisionerOldDynamicRulesetEnabledLevelVal  INTEGER
	}

psmProvisionerOldDynamicRulesetEnabledLevelName OBJECT-TYPE
	SYNTAX      DisplayString
	MAX-ACCESS  not-accessible
	STATUS      current
	DESCRIPTION
	"Dynamic ruleset enabled"
	::={ psmProvisionerOldDynamicRulesetEnabledLevelEntry 1}

psmProvisionerOldDynamicRulesetEnabledLevelVal OBJECT-TYPE
	SYNTAX     INTEGER {
		false(0),
		true(1)
	}
	MAX-ACCESS read-only
	STATUS     current
	DESCRIPTION
	"Dynamic ruleset enabled"
	::={ psmProvisionerOldDynamicRulesetEnabledLevelEntry 2 }

psmProvisionerOldDynamicRulesetStateChange OBJECT IDENTIFIER ::= { psmProvisionerOld 29 }

psmProvisionerOldDynamicRulesetStateChangeVal OBJECT-TYPE
	SYNTAX     DateAndTime
	MAX-ACCESS read-only
	STATUS     current
	DESCRIPTION "Dynamic ruleset state change"

	::={ psmProvisionerOldDynamicRulesetStateChange 1 }

psmProvisionerOldDynamicRulesetStateChangeLevelTable OBJECT-TYPE
	SYNTAX     SEQUENCE OF PsmProvisionerOldDynamicRulesetStateChangeLevelEntry
	MAX-ACCESS not-accessible
	STATUS     current
	DESCRIPTION
	"Dynamic ruleset state change"
	::={ psmProvisionerOldDynamicRulesetStateChange 4 }

psmProvisionerOldDynamicRulesetStateChangeLevelEntry OBJECT-TYPE
	SYNTAX      PsmProvisionerOldDynamicRulesetStateChangeLevelEntry
	MAX-ACCESS  not-accessible
	STATUS      current
	DESCRIPTION
	"Dynamic ruleset state change"
	INDEX { psmProvisionerOldDynamicRulesetStateChangeLevelName }
	::={ psmProvisionerOldDynamicRulesetStateChangeLevelTable 1 }

PsmProvisionerOldDynamicRulesetStateChangeLevelEntry ::=
	SEQUENCE {
		psmProvisionerOldDynamicRulesetStateChangeLevelName DisplayString,
		psmProvisionerOldDynamicRulesetStateChangeLevelVal  DateAndTime
	}

psmProvisionerOldDynamicRulesetStateChangeLevelName OBJECT-TYPE
	SYNTAX      DisplayString
	MAX-ACCESS  not-accessible
	STATUS      current
	DESCRIPTION
	"Dynamic ruleset state change"
	::={ psmProvisionerOldDynamicRulesetStateChangeLevelEntry 1}

psmProvisionerOldDynamicRulesetStateChangeLevelVal OBJECT-TYPE
	SYNTAX     DateAndTime
	MAX-ACCESS read-only
	STATUS     current
	DESCRIPTION
	"Dynamic ruleset state change"
	::={ psmProvisionerOldDynamicRulesetStateChangeLevelEntry 2 }

psmProvisionerOldDynamicRulesetNextReconnectTime OBJECT IDENTIFIER ::= { psmProvisionerOld 30 }

psmProvisionerOldDynamicRulesetNextReconnectTimeVal OBJECT-TYPE
	SYNTAX     DateAndTime
	MAX-ACCESS read-only
	STATUS     current
	DESCRIPTION "Dynamic ruleset next reconnect time"

	::={ psmProvisionerOldDynamicRulesetNextReconnectTime 1 }

psmProvisionerOldDynamicRulesetNextReconnectTimeLevelTable OBJECT-TYPE
	SYNTAX     SEQUENCE OF PsmProvisionerOldDynamicRulesetNextReconnectTimeLevelEntry
	MAX-ACCESS not-accessible
	STATUS     current
	DESCRIPTION
	"Dynamic ruleset next reconnect time"
	::={ psmProvisionerOldDynamicRulesetNextReconnectTime 4 }

psmProvisionerOldDynamicRulesetNextReconnectTimeLevelEntry OBJECT-TYPE
	SYNTAX      PsmProvisionerOldDynamicRulesetNextReconnectTimeLevelEntry
	MAX-ACCESS  not-accessible
	STATUS      current
	DESCRIPTION
	"Dynamic ruleset next reconnect time"
	INDEX { psmProvisionerOldDynamicRulesetNextReconnectTimeLevelName }
	::={ psmProvisionerOldDynamicRulesetNextReconnectTimeLevelTable 1 }

PsmProvisionerOldDynamicRulesetNextReconnectTimeLevelEntry ::=
	SEQUENCE {
		psmProvisionerOldDynamicRulesetNextReconnectTimeLevelName DisplayString,
		psmProvisionerOldDynamicRulesetNextReconnectTimeLevelVal  DateAndTime
	}

psmProvisionerOldDynamicRulesetNextReconnectTimeLevelName OBJECT-TYPE
	SYNTAX      DisplayString
	MAX-ACCESS  not-accessible
	STATUS      current
	DESCRIPTION
	"Dynamic ruleset next reconnect time"
	::={ psmProvisionerOldDynamicRulesetNextReconnectTimeLevelEntry 1}

psmProvisionerOldDynamicRulesetNextReconnectTimeLevelVal OBJECT-TYPE
	SYNTAX     DateAndTime
	MAX-ACCESS read-only
	STATUS     current
	DESCRIPTION
	"Dynamic ruleset next reconnect time"
	::={ psmProvisionerOldDynamicRulesetNextReconnectTimeLevelEntry 2 }

psmProvisionerOldDynamicRulesetReconnects OBJECT IDENTIFIER ::= { psmProvisionerOld 31 }

psmProvisionerOldDynamicRulesetReconnectsVal OBJECT-TYPE
	SYNTAX     Counter64
	MAX-ACCESS read-only
	STATUS     current
	DESCRIPTION "Dynamic ruleset reconnects"

	::={ psmProvisionerOldDynamicRulesetReconnects 1 }

psmProvisionerOldDynamicRulesetReconnectsMom OBJECT-TYPE
	SYNTAX     CounterBasedGauge64
	MAX-ACCESS read-only
	STATUS     current
	DESCRIPTION "Dynamic ruleset reconnects"

	::={ psmProvisionerOldDynamicRulesetReconnects 2 }

psmProvisionerOldDynamicRulesetReconnectsMax OBJECT-TYPE
	SYNTAX     CounterBasedGauge64
	MAX-ACCESS read-only
	STATUS     current
	DESCRIPTION "Dynamic ruleset reconnects"

	::={ psmProvisionerOldDynamicRulesetReconnects 3 }

psmProvisionerOldDynamicRulesetReconnectsLevelTable OBJECT-TYPE
	SYNTAX     SEQUENCE OF PsmProvisionerOldDynamicRulesetReconnectsLevelEntry
	MAX-ACCESS not-accessible
	STATUS     current
	DESCRIPTION
	"Dynamic ruleset reconnects"
	::={ psmProvisionerOldDynamicRulesetReconnects 4 }

psmProvisionerOldDynamicRulesetReconnectsLevelEntry OBJECT-TYPE
	SYNTAX      PsmProvisionerOldDynamicRulesetReconnectsLevelEntry
	MAX-ACCESS  not-accessible
	STATUS      current
	DESCRIPTION
	"Dynamic ruleset reconnects"
	INDEX { psmProvisionerOldDynamicRulesetReconnectsLevelName }
	::={ psmProvisionerOldDynamicRulesetReconnectsLevelTable 1 }

PsmProvisionerOldDynamicRulesetReconnectsLevelEntry ::=
	SEQUENCE {
		psmProvisionerOldDynamicRulesetReconnectsLevelName DisplayString,
		psmProvisionerOldDynamicRulesetReconnectsLevelVal  Counter64,
		psmProvisionerOldDynamicRulesetReconnectsLevelMom  CounterBasedGauge64,
		psmProvisionerOldDynamicRulesetReconnectsLevelMax  CounterBasedGauge64
	}

psmProvisionerOldDynamicRulesetReconnectsLevelName OBJECT-TYPE
	SYNTAX      DisplayString
	MAX-ACCESS  not-accessible
	STATUS      current
	DESCRIPTION
	"Dynamic ruleset reconnects"
	::={ psmProvisionerOldDynamicRulesetReconnectsLevelEntry 1}

psmProvisionerOldDynamicRulesetReconnectsLevelVal OBJECT-TYPE
	SYNTAX     Counter64
	MAX-ACCESS read-only
	STATUS     current
	DESCRIPTION
	"Dynamic ruleset reconnects"
	::={ psmProvisionerOldDynamicRulesetReconnectsLevelEntry 2 }

psmProvisionerOldDynamicRulesetReconnectsLevelMom OBJECT-TYPE
	SYNTAX     CounterBasedGauge64
	MAX-ACCESS read-only
	STATUS     current
	DESCRIPTION
	"Dynamic ruleset reconnects"
	::={ psmProvisionerOldDynamicRulesetReconnectsLevelEntry 3 }

psmProvisionerOldDynamicRulesetReconnectsLevelMax OBJECT-TYPE
	SYNTAX     CounterBasedGauge64
	MAX-ACCESS read-only
	STATUS     current
	DESCRIPTION
	"Dynamic ruleset reconnects"
	::={ psmProvisionerOldDynamicRulesetReconnectsLevelEntry 4 }

psmProvisionerOldDynamicRulesetState OBJECT IDENTIFIER ::= { psmProvisionerOld 32 }

psmProvisionerOldDynamicRulesetStateVal OBJECT-TYPE
	SYNTAX     INTEGER {
		unconfigured(0),
		disconnected(1),
		requestRootNetobject(2),
		connecting(3),
		requestingSnapshot(4),
		connected(5),
		synchronizeInit(6),
		synchronizing(7),
		catchup(8),
		online(9)
	}
	MAX-ACCESS read-only
	STATUS     current
	DESCRIPTION "Dynamic ruleset state"

	::={ psmProvisionerOldDynamicRulesetState 1 }

psmProvisionerOldDynamicRulesetStateLevelTable OBJECT-TYPE
	SYNTAX     SEQUENCE OF PsmProvisionerOldDynamicRulesetStateLevelEntry
	MAX-ACCESS not-accessible
	STATUS     current
	DESCRIPTION
	"Dynamic ruleset state"
	::={ psmProvisionerOldDynamicRulesetState 4 }

psmProvisionerOldDynamicRulesetStateLevelEntry OBJECT-TYPE
	SYNTAX      PsmProvisionerOldDynamicRulesetStateLevelEntry
	MAX-ACCESS  not-accessible
	STATUS      current
	DESCRIPTION
	"Dynamic ruleset state"
	INDEX { psmProvisionerOldDynamicRulesetStateLevelName }
	::={ psmProvisionerOldDynamicRulesetStateLevelTable 1 }

PsmProvisionerOldDynamicRulesetStateLevelEntry ::=
	SEQUENCE {
		psmProvisionerOldDynamicRulesetStateLevelName DisplayString,
		psmProvisionerOldDynamicRulesetStateLevelVal  INTEGER
	}

psmProvisionerOldDynamicRulesetStateLevelName OBJECT-TYPE
	SYNTAX      DisplayString
	MAX-ACCESS  not-accessible
	STATUS      current
	DESCRIPTION
	"Dynamic ruleset state"
	::={ psmProvisionerOldDynamicRulesetStateLevelEntry 1}

psmProvisionerOldDynamicRulesetStateLevelVal OBJECT-TYPE
	SYNTAX     INTEGER {
		unconfigured(0),
		disconnected(1),
		requestRootNetobject(2),
		connecting(3),
		requestingSnapshot(4),
		connected(5),
		synchronizeInit(6),
		synchronizing(7),
		catchup(8),
		online(9)
	}
	MAX-ACCESS read-only
	STATUS     current
	DESCRIPTION
	"Dynamic ruleset state"
	::={ psmProvisionerOldDynamicRulesetStateLevelEntry 2 }

psmProvisionerOldConnectionBytesReceived OBJECT IDENTIFIER ::= { psmProvisionerOld 33 }

psmProvisionerOldConnectionBytesReceivedVal OBJECT-TYPE
	SYNTAX     Counter64
	MAX-ACCESS read-only
	STATUS     current
	DESCRIPTION "Connection bytes received"

	::={ psmProvisionerOldConnectionBytesReceived 1 }

psmProvisionerOldConnectionBytesReceivedMom OBJECT-TYPE
	SYNTAX     CounterBasedGauge64
	MAX-ACCESS read-only
	STATUS     current
	DESCRIPTION "Connection bytes received"

	::={ psmProvisionerOldConnectionBytesReceived 2 }

psmProvisionerOldConnectionBytesReceivedMax OBJECT-TYPE
	SYNTAX     CounterBasedGauge64
	MAX-ACCESS read-only
	STATUS     current
	DESCRIPTION "Connection bytes received"

	::={ psmProvisionerOldConnectionBytesReceived 3 }

psmProvisionerOldConnectionBytesReceivedLevelTable OBJECT-TYPE
	SYNTAX     SEQUENCE OF PsmProvisionerOldConnectionBytesReceivedLevelEntry
	MAX-ACCESS not-accessible
	STATUS     current
	DESCRIPTION
	"Connection bytes received"
	::={ psmProvisionerOldConnectionBytesReceived 4 }

psmProvisionerOldConnectionBytesReceivedLevelEntry OBJECT-TYPE
	SYNTAX      PsmProvisionerOldConnectionBytesReceivedLevelEntry
	MAX-ACCESS  not-accessible
	STATUS      current
	DESCRIPTION
	"Connection bytes received"
	INDEX { psmProvisionerOldConnectionBytesReceivedLevelName }
	::={ psmProvisionerOldConnectionBytesReceivedLevelTable 1 }

PsmProvisionerOldConnectionBytesReceivedLevelEntry ::=
	SEQUENCE {
		psmProvisionerOldConnectionBytesReceivedLevelName DisplayString,
		psmProvisionerOldConnectionBytesReceivedLevelVal  Counter64,
		psmProvisionerOldConnectionBytesReceivedLevelMom  CounterBasedGauge64,
		psmProvisionerOldConnectionBytesReceivedLevelMax  CounterBasedGauge64
	}

psmProvisionerOldConnectionBytesReceivedLevelName OBJECT-TYPE
	SYNTAX      DisplayString
	MAX-ACCESS  not-accessible
	STATUS      current
	DESCRIPTION
	"Connection bytes received"
	::={ psmProvisionerOldConnectionBytesReceivedLevelEntry 1}

psmProvisionerOldConnectionBytesReceivedLevelVal OBJECT-TYPE
	SYNTAX     Counter64
	MAX-ACCESS read-only
	STATUS     current
	DESCRIPTION
	"Connection bytes received"
	::={ psmProvisionerOldConnectionBytesReceivedLevelEntry 2 }

psmProvisionerOldConnectionBytesReceivedLevelMom OBJECT-TYPE
	SYNTAX     CounterBasedGauge64
	MAX-ACCESS read-only
	STATUS     current
	DESCRIPTION
	"Connection bytes received"
	::={ psmProvisionerOldConnectionBytesReceivedLevelEntry 3 }

psmProvisionerOldConnectionBytesReceivedLevelMax OBJECT-TYPE
	SYNTAX     CounterBasedGauge64
	MAX-ACCESS read-only
	STATUS     current
	DESCRIPTION
	"Connection bytes received"
	::={ psmProvisionerOldConnectionBytesReceivedLevelEntry 4 }

psmProvisionerOldConnectionBytesSent OBJECT IDENTIFIER ::= { psmProvisionerOld 34 }

psmProvisionerOldConnectionBytesSentVal OBJECT-TYPE
	SYNTAX     Counter64
	MAX-ACCESS read-only
	STATUS     current
	DESCRIPTION "Connection bytes sent"

	::={ psmProvisionerOldConnectionBytesSent 1 }

psmProvisionerOldConnectionBytesSentMom OBJECT-TYPE
	SYNTAX     CounterBasedGauge64
	MAX-ACCESS read-only
	STATUS     current
	DESCRIPTION "Connection bytes sent"

	::={ psmProvisionerOldConnectionBytesSent 2 }

psmProvisionerOldConnectionBytesSentMax OBJECT-TYPE
	SYNTAX     CounterBasedGauge64
	MAX-ACCESS read-only
	STATUS     current
	DESCRIPTION "Connection bytes sent"

	::={ psmProvisionerOldConnectionBytesSent 3 }

psmProvisionerOldConnectionBytesSentLevelTable OBJECT-TYPE
	SYNTAX     SEQUENCE OF PsmProvisionerOldConnectionBytesSentLevelEntry
	MAX-ACCESS not-accessible
	STATUS     current
	DESCRIPTION
	"Connection bytes sent"
	::={ psmProvisionerOldConnectionBytesSent 4 }

psmProvisionerOldConnectionBytesSentLevelEntry OBJECT-TYPE
	SYNTAX      PsmProvisionerOldConnectionBytesSentLevelEntry
	MAX-ACCESS  not-accessible
	STATUS      current
	DESCRIPTION
	"Connection bytes sent"
	INDEX { psmProvisionerOldConnectionBytesSentLevelName }
	::={ psmProvisionerOldConnectionBytesSentLevelTable 1 }

PsmProvisionerOldConnectionBytesSentLevelEntry ::=
	SEQUENCE {
		psmProvisionerOldConnectionBytesSentLevelName DisplayString,
		psmProvisionerOldConnectionBytesSentLevelVal  Counter64,
		psmProvisionerOldConnectionBytesSentLevelMom  CounterBasedGauge64,
		psmProvisionerOldConnectionBytesSentLevelMax  CounterBasedGauge64
	}

psmProvisionerOldConnectionBytesSentLevelName OBJECT-TYPE
	SYNTAX      DisplayString
	MAX-ACCESS  not-accessible
	STATUS      current
	DESCRIPTION
	"Connection bytes sent"
	::={ psmProvisionerOldConnectionBytesSentLevelEntry 1}

psmProvisionerOldConnectionBytesSentLevelVal OBJECT-TYPE
	SYNTAX     Counter64
	MAX-ACCESS read-only
	STATUS     current
	DESCRIPTION
	"Connection bytes sent"
	::={ psmProvisionerOldConnectionBytesSentLevelEntry 2 }

psmProvisionerOldConnectionBytesSentLevelMom OBJECT-TYPE
	SYNTAX     CounterBasedGauge64
	MAX-ACCESS read-only
	STATUS     current
	DESCRIPTION
	"Connection bytes sent"
	::={ psmProvisionerOldConnectionBytesSentLevelEntry 3 }

psmProvisionerOldConnectionBytesSentLevelMax OBJECT-TYPE
	SYNTAX     CounterBasedGauge64
	MAX-ACCESS read-only
	STATUS     current
	DESCRIPTION
	"Connection bytes sent"
	::={ psmProvisionerOldConnectionBytesSentLevelEntry 4 }

psmSourceCounters OBJECT IDENTIFIER ::= { psmv2 4 }

psmSourceCountersBytes OBJECT IDENTIFIER ::= { psmSourceCounters 1 }

psmSourceCountersBytesVal OBJECT-TYPE
	SYNTAX     Counter64
	MAX-ACCESS read-only
	STATUS     current
	DESCRIPTION "Bytes"

	::={ psmSourceCountersBytes 1 }

psmSourceCountersBytesMom OBJECT-TYPE
	SYNTAX     CounterBasedGauge64
	MAX-ACCESS read-only
	STATUS     current
	DESCRIPTION "Bytes"

	::={ psmSourceCountersBytes 2 }

psmSourceCountersBytesMax OBJECT-TYPE
	SYNTAX     CounterBasedGauge64
	MAX-ACCESS read-only
	STATUS     current
	DESCRIPTION "Bytes"

	::={ psmSourceCountersBytes 3 }

psmSourceCountersBytesLevelTable OBJECT-TYPE
	SYNTAX     SEQUENCE OF PsmSourceCountersBytesLevelEntry
	MAX-ACCESS not-accessible
	STATUS     current
	DESCRIPTION
	"Bytes"
	::={ psmSourceCountersBytes 4 }

psmSourceCountersBytesLevelEntry OBJECT-TYPE
	SYNTAX      PsmSourceCountersBytesLevelEntry
	MAX-ACCESS  not-accessible
	STATUS      current
	DESCRIPTION
	"Bytes"
	INDEX { psmSourceCountersBytesLevelName }
	::={ psmSourceCountersBytesLevelTable 1 }

PsmSourceCountersBytesLevelEntry ::=
	SEQUENCE {
		psmSourceCountersBytesLevelName DisplayString,
		psmSourceCountersBytesLevelVal  Counter64,
		psmSourceCountersBytesLevelMom  CounterBasedGauge64,
		psmSourceCountersBytesLevelMax  CounterBasedGauge64
	}

psmSourceCountersBytesLevelName OBJECT-TYPE
	SYNTAX      DisplayString
	MAX-ACCESS  not-accessible
	STATUS      current
	DESCRIPTION
	"Bytes"
	::={ psmSourceCountersBytesLevelEntry 1}

psmSourceCountersBytesLevelVal OBJECT-TYPE
	SYNTAX     Counter64
	MAX-ACCESS read-only
	STATUS     current
	DESCRIPTION
	"Bytes"
	::={ psmSourceCountersBytesLevelEntry 2 }

psmSourceCountersBytesLevelMom OBJECT-TYPE
	SYNTAX     CounterBasedGauge64
	MAX-ACCESS read-only
	STATUS     current
	DESCRIPTION
	"Bytes"
	::={ psmSourceCountersBytesLevelEntry 3 }

psmSourceCountersBytesLevelMax OBJECT-TYPE
	SYNTAX     CounterBasedGauge64
	MAX-ACCESS read-only
	STATUS     current
	DESCRIPTION
	"Bytes"
	::={ psmSourceCountersBytesLevelEntry 4 }

psmSourceCountersUpdates OBJECT IDENTIFIER ::= { psmSourceCounters 2 }

psmSourceCountersUpdatesVal OBJECT-TYPE
	SYNTAX     Counter64
	MAX-ACCESS read-only
	STATUS     current
	DESCRIPTION "Updates"

	::={ psmSourceCountersUpdates 1 }

psmSourceCountersUpdatesMom OBJECT-TYPE
	SYNTAX     CounterBasedGauge64
	MAX-ACCESS read-only
	STATUS     current
	DESCRIPTION "Updates"

	::={ psmSourceCountersUpdates 2 }

psmSourceCountersUpdatesMax OBJECT-TYPE
	SYNTAX     CounterBasedGauge64
	MAX-ACCESS read-only
	STATUS     current
	DESCRIPTION "Updates"

	::={ psmSourceCountersUpdates 3 }

psmSourceCountersUpdatesLevelTable OBJECT-TYPE
	SYNTAX     SEQUENCE OF PsmSourceCountersUpdatesLevelEntry
	MAX-ACCESS not-accessible
	STATUS     current
	DESCRIPTION
	"Updates"
	::={ psmSourceCountersUpdates 4 }

psmSourceCountersUpdatesLevelEntry OBJECT-TYPE
	SYNTAX      PsmSourceCountersUpdatesLevelEntry
	MAX-ACCESS  not-accessible
	STATUS      current
	DESCRIPTION
	"Updates"
	INDEX { psmSourceCountersUpdatesLevelName }
	::={ psmSourceCountersUpdatesLevelTable 1 }

PsmSourceCountersUpdatesLevelEntry ::=
	SEQUENCE {
		psmSourceCountersUpdatesLevelName DisplayString,
		psmSourceCountersUpdatesLevelVal  Counter64,
		psmSourceCountersUpdatesLevelMom  CounterBasedGauge64,
		psmSourceCountersUpdatesLevelMax  CounterBasedGauge64
	}

psmSourceCountersUpdatesLevelName OBJECT-TYPE
	SYNTAX      DisplayString
	MAX-ACCESS  not-accessible
	STATUS      current
	DESCRIPTION
	"Updates"
	::={ psmSourceCountersUpdatesLevelEntry 1}

psmSourceCountersUpdatesLevelVal OBJECT-TYPE
	SYNTAX     Counter64
	MAX-ACCESS read-only
	STATUS     current
	DESCRIPTION
	"Updates"
	::={ psmSourceCountersUpdatesLevelEntry 2 }

psmSourceCountersUpdatesLevelMom OBJECT-TYPE
	SYNTAX     CounterBasedGauge64
	MAX-ACCESS read-only
	STATUS     current
	DESCRIPTION
	"Updates"
	::={ psmSourceCountersUpdatesLevelEntry 3 }

psmSourceCountersUpdatesLevelMax OBJECT-TYPE
	SYNTAX     CounterBasedGauge64
	MAX-ACCESS read-only
	STATUS     current
	DESCRIPTION
	"Updates"
	::={ psmSourceCountersUpdatesLevelEntry 4 }

psmSourceUDP OBJECT IDENTIFIER ::= { psmv2 6 }

psmSourceUDPFailures OBJECT IDENTIFIER ::= { psmSourceUDP 1 }

psmSourceUDPFailuresVal OBJECT-TYPE
	SYNTAX     Counter64
	MAX-ACCESS read-only
	STATUS     current
	DESCRIPTION "Failures"

	::={ psmSourceUDPFailures 1 }

psmSourceUDPFailuresMom OBJECT-TYPE
	SYNTAX     CounterBasedGauge64
	MAX-ACCESS read-only
	STATUS     current
	DESCRIPTION "Failures"

	::={ psmSourceUDPFailures 2 }

psmSourceUDPFailuresMax OBJECT-TYPE
	SYNTAX     CounterBasedGauge64
	MAX-ACCESS read-only
	STATUS     current
	DESCRIPTION "Failures"

	::={ psmSourceUDPFailures 3 }

psmSourceUDPFailuresLevelTable OBJECT-TYPE
	SYNTAX     SEQUENCE OF PsmSourceUDPFailuresLevelEntry
	MAX-ACCESS not-accessible
	STATUS     current
	DESCRIPTION
	"Failures"
	::={ psmSourceUDPFailures 4 }

psmSourceUDPFailuresLevelEntry OBJECT-TYPE
	SYNTAX      PsmSourceUDPFailuresLevelEntry
	MAX-ACCESS  not-accessible
	STATUS      current
	DESCRIPTION
	"Failures"
	INDEX { psmSourceUDPFailuresLevelName }
	::={ psmSourceUDPFailuresLevelTable 1 }

PsmSourceUDPFailuresLevelEntry ::=
	SEQUENCE {
		psmSourceUDPFailuresLevelName DisplayString,
		psmSourceUDPFailuresLevelVal  Counter64,
		psmSourceUDPFailuresLevelMom  CounterBasedGauge64,
		psmSourceUDPFailuresLevelMax  CounterBasedGauge64
	}

psmSourceUDPFailuresLevelName OBJECT-TYPE
	SYNTAX      DisplayString
	MAX-ACCESS  not-accessible
	STATUS      current
	DESCRIPTION
	"Failures"
	::={ psmSourceUDPFailuresLevelEntry 1}

psmSourceUDPFailuresLevelVal OBJECT-TYPE
	SYNTAX     Counter64
	MAX-ACCESS read-only
	STATUS     current
	DESCRIPTION
	"Failures"
	::={ psmSourceUDPFailuresLevelEntry 2 }

psmSourceUDPFailuresLevelMom OBJECT-TYPE
	SYNTAX     CounterBasedGauge64
	MAX-ACCESS read-only
	STATUS     current
	DESCRIPTION
	"Failures"
	::={ psmSourceUDPFailuresLevelEntry 3 }

psmSourceUDPFailuresLevelMax OBJECT-TYPE
	SYNTAX     CounterBasedGauge64
	MAX-ACCESS read-only
	STATUS     current
	DESCRIPTION
	"Failures"
	::={ psmSourceUDPFailuresLevelEntry 4 }

psmSourceUDPRejects OBJECT IDENTIFIER ::= { psmSourceUDP 2 }

psmSourceUDPRejectsVal OBJECT-TYPE
	SYNTAX     Counter64
	MAX-ACCESS read-only
	STATUS     current
	DESCRIPTION "Rejects"

	::={ psmSourceUDPRejects 1 }

psmSourceUDPRejectsMom OBJECT-TYPE
	SYNTAX     CounterBasedGauge64
	MAX-ACCESS read-only
	STATUS     current
	DESCRIPTION "Rejects"

	::={ psmSourceUDPRejects 2 }

psmSourceUDPRejectsMax OBJECT-TYPE
	SYNTAX     CounterBasedGauge64
	MAX-ACCESS read-only
	STATUS     current
	DESCRIPTION "Rejects"

	::={ psmSourceUDPRejects 3 }

psmSourceUDPRejectsLevelTable OBJECT-TYPE
	SYNTAX     SEQUENCE OF PsmSourceUDPRejectsLevelEntry
	MAX-ACCESS not-accessible
	STATUS     current
	DESCRIPTION
	"Rejects"
	::={ psmSourceUDPRejects 4 }

psmSourceUDPRejectsLevelEntry OBJECT-TYPE
	SYNTAX      PsmSourceUDPRejectsLevelEntry
	MAX-ACCESS  not-accessible
	STATUS      current
	DESCRIPTION
	"Rejects"
	INDEX { psmSourceUDPRejectsLevelName }
	::={ psmSourceUDPRejectsLevelTable 1 }

PsmSourceUDPRejectsLevelEntry ::=
	SEQUENCE {
		psmSourceUDPRejectsLevelName DisplayString,
		psmSourceUDPRejectsLevelVal  Counter64,
		psmSourceUDPRejectsLevelMom  CounterBasedGauge64,
		psmSourceUDPRejectsLevelMax  CounterBasedGauge64
	}

psmSourceUDPRejectsLevelName OBJECT-TYPE
	SYNTAX      DisplayString
	MAX-ACCESS  not-accessible
	STATUS      current
	DESCRIPTION
	"Rejects"
	::={ psmSourceUDPRejectsLevelEntry 1}

psmSourceUDPRejectsLevelVal OBJECT-TYPE
	SYNTAX     Counter64
	MAX-ACCESS read-only
	STATUS     current
	DESCRIPTION
	"Rejects"
	::={ psmSourceUDPRejectsLevelEntry 2 }

psmSourceUDPRejectsLevelMom OBJECT-TYPE
	SYNTAX     CounterBasedGauge64
	MAX-ACCESS read-only
	STATUS     current
	DESCRIPTION
	"Rejects"
	::={ psmSourceUDPRejectsLevelEntry 3 }

psmSourceUDPRejectsLevelMax OBJECT-TYPE
	SYNTAX     CounterBasedGauge64
	MAX-ACCESS read-only
	STATUS     current
	DESCRIPTION
	"Rejects"
	::={ psmSourceUDPRejectsLevelEntry 4 }

psmSourceUDPRequests OBJECT IDENTIFIER ::= { psmSourceUDP 3 }

psmSourceUDPRequestsVal OBJECT-TYPE
	SYNTAX     Counter64
	MAX-ACCESS read-only
	STATUS     current
	DESCRIPTION "Requests"

	::={ psmSourceUDPRequests 1 }

psmSourceUDPRequestsMom OBJECT-TYPE
	SYNTAX     CounterBasedGauge64
	MAX-ACCESS read-only
	STATUS     current
	DESCRIPTION "Requests"

	::={ psmSourceUDPRequests 2 }

psmSourceUDPRequestsMax OBJECT-TYPE
	SYNTAX     CounterBasedGauge64
	MAX-ACCESS read-only
	STATUS     current
	DESCRIPTION "Requests"

	::={ psmSourceUDPRequests 3 }

psmSourceUDPRequestsLevelTable OBJECT-TYPE
	SYNTAX     SEQUENCE OF PsmSourceUDPRequestsLevelEntry
	MAX-ACCESS not-accessible
	STATUS     current
	DESCRIPTION
	"Requests"
	::={ psmSourceUDPRequests 4 }

psmSourceUDPRequestsLevelEntry OBJECT-TYPE
	SYNTAX      PsmSourceUDPRequestsLevelEntry
	MAX-ACCESS  not-accessible
	STATUS      current
	DESCRIPTION
	"Requests"
	INDEX { psmSourceUDPRequestsLevelName }
	::={ psmSourceUDPRequestsLevelTable 1 }

PsmSourceUDPRequestsLevelEntry ::=
	SEQUENCE {
		psmSourceUDPRequestsLevelName DisplayString,
		psmSourceUDPRequestsLevelVal  Counter64,
		psmSourceUDPRequestsLevelMom  CounterBasedGauge64,
		psmSourceUDPRequestsLevelMax  CounterBasedGauge64
	}

psmSourceUDPRequestsLevelName OBJECT-TYPE
	SYNTAX      DisplayString
	MAX-ACCESS  not-accessible
	STATUS      current
	DESCRIPTION
	"Requests"
	::={ psmSourceUDPRequestsLevelEntry 1}

psmSourceUDPRequestsLevelVal OBJECT-TYPE
	SYNTAX     Counter64
	MAX-ACCESS read-only
	STATUS     current
	DESCRIPTION
	"Requests"
	::={ psmSourceUDPRequestsLevelEntry 2 }

psmSourceUDPRequestsLevelMom OBJECT-TYPE
	SYNTAX     CounterBasedGauge64
	MAX-ACCESS read-only
	STATUS     current
	DESCRIPTION
	"Requests"
	::={ psmSourceUDPRequestsLevelEntry 3 }

psmSourceUDPRequestsLevelMax OBJECT-TYPE
	SYNTAX     CounterBasedGauge64
	MAX-ACCESS read-only
	STATUS     current
	DESCRIPTION
	"Requests"
	::={ psmSourceUDPRequestsLevelEntry 4 }

psmSourceHosts OBJECT IDENTIFIER ::= { psmv2 13 }

psmSourceHostsFailures OBJECT IDENTIFIER ::= { psmSourceHosts 1 }

psmSourceHostsFailuresVal OBJECT-TYPE
	SYNTAX     Counter64
	MAX-ACCESS read-only
	STATUS     current
	DESCRIPTION "Failures"

	::={ psmSourceHostsFailures 1 }

psmSourceHostsFailuresMom OBJECT-TYPE
	SYNTAX     CounterBasedGauge64
	MAX-ACCESS read-only
	STATUS     current
	DESCRIPTION "Failures"

	::={ psmSourceHostsFailures 2 }

psmSourceHostsFailuresMax OBJECT-TYPE
	SYNTAX     CounterBasedGauge64
	MAX-ACCESS read-only
	STATUS     current
	DESCRIPTION "Failures"

	::={ psmSourceHostsFailures 3 }

psmSourceHostsFailuresLevelTable OBJECT-TYPE
	SYNTAX     SEQUENCE OF PsmSourceHostsFailuresLevelEntry
	MAX-ACCESS not-accessible
	STATUS     current
	DESCRIPTION
	"Failures"
	::={ psmSourceHostsFailures 4 }

psmSourceHostsFailuresLevelEntry OBJECT-TYPE
	SYNTAX      PsmSourceHostsFailuresLevelEntry
	MAX-ACCESS  not-accessible
	STATUS      current
	DESCRIPTION
	"Failures"
	INDEX { psmSourceHostsFailuresLevelName }
	::={ psmSourceHostsFailuresLevelTable 1 }

PsmSourceHostsFailuresLevelEntry ::=
	SEQUENCE {
		psmSourceHostsFailuresLevelName DisplayString,
		psmSourceHostsFailuresLevelVal  Counter64,
		psmSourceHostsFailuresLevelMom  CounterBasedGauge64,
		psmSourceHostsFailuresLevelMax  CounterBasedGauge64
	}

psmSourceHostsFailuresLevelName OBJECT-TYPE
	SYNTAX      DisplayString
	MAX-ACCESS  not-accessible
	STATUS      current
	DESCRIPTION
	"Failures"
	::={ psmSourceHostsFailuresLevelEntry 1}

psmSourceHostsFailuresLevelVal OBJECT-TYPE
	SYNTAX     Counter64
	MAX-ACCESS read-only
	STATUS     current
	DESCRIPTION
	"Failures"
	::={ psmSourceHostsFailuresLevelEntry 2 }

psmSourceHostsFailuresLevelMom OBJECT-TYPE
	SYNTAX     CounterBasedGauge64
	MAX-ACCESS read-only
	STATUS     current
	DESCRIPTION
	"Failures"
	::={ psmSourceHostsFailuresLevelEntry 3 }

psmSourceHostsFailuresLevelMax OBJECT-TYPE
	SYNTAX     CounterBasedGauge64
	MAX-ACCESS read-only
	STATUS     current
	DESCRIPTION
	"Failures"
	::={ psmSourceHostsFailuresLevelEntry 4 }

psmSourceHostsRequests OBJECT IDENTIFIER ::= { psmSourceHosts 2 }

psmSourceHostsRequestsVal OBJECT-TYPE
	SYNTAX     Counter64
	MAX-ACCESS read-only
	STATUS     current
	DESCRIPTION "Requests"

	::={ psmSourceHostsRequests 1 }

psmSourceHostsRequestsMom OBJECT-TYPE
	SYNTAX     CounterBasedGauge64
	MAX-ACCESS read-only
	STATUS     current
	DESCRIPTION "Requests"

	::={ psmSourceHostsRequests 2 }

psmSourceHostsRequestsMax OBJECT-TYPE
	SYNTAX     CounterBasedGauge64
	MAX-ACCESS read-only
	STATUS     current
	DESCRIPTION "Requests"

	::={ psmSourceHostsRequests 3 }

psmSourceHostsRequestsLevelTable OBJECT-TYPE
	SYNTAX     SEQUENCE OF PsmSourceHostsRequestsLevelEntry
	MAX-ACCESS not-accessible
	STATUS     current
	DESCRIPTION
	"Requests"
	::={ psmSourceHostsRequests 4 }

psmSourceHostsRequestsLevelEntry OBJECT-TYPE
	SYNTAX      PsmSourceHostsRequestsLevelEntry
	MAX-ACCESS  not-accessible
	STATUS      current
	DESCRIPTION
	"Requests"
	INDEX { psmSourceHostsRequestsLevelName }
	::={ psmSourceHostsRequestsLevelTable 1 }

PsmSourceHostsRequestsLevelEntry ::=
	SEQUENCE {
		psmSourceHostsRequestsLevelName DisplayString,
		psmSourceHostsRequestsLevelVal  Counter64,
		psmSourceHostsRequestsLevelMom  CounterBasedGauge64,
		psmSourceHostsRequestsLevelMax  CounterBasedGauge64
	}

psmSourceHostsRequestsLevelName OBJECT-TYPE
	SYNTAX      DisplayString
	MAX-ACCESS  not-accessible
	STATUS      current
	DESCRIPTION
	"Requests"
	::={ psmSourceHostsRequestsLevelEntry 1}

psmSourceHostsRequestsLevelVal OBJECT-TYPE
	SYNTAX     Counter64
	MAX-ACCESS read-only
	STATUS     current
	DESCRIPTION
	"Requests"
	::={ psmSourceHostsRequestsLevelEntry 2 }

psmSourceHostsRequestsLevelMom OBJECT-TYPE
	SYNTAX     CounterBasedGauge64
	MAX-ACCESS read-only
	STATUS     current
	DESCRIPTION
	"Requests"
	::={ psmSourceHostsRequestsLevelEntry 3 }

psmSourceHostsRequestsLevelMax OBJECT-TYPE
	SYNTAX     CounterBasedGauge64
	MAX-ACCESS read-only
	STATUS     current
	DESCRIPTION
	"Requests"
	::={ psmSourceHostsRequestsLevelEntry 4 }

psmModel OBJECT IDENTIFIER ::= { psmv2 1 }

psmModelServerConnections OBJECT IDENTIFIER ::= { psmModel 1 }

psmModelServerConnectionsVal OBJECT-TYPE
	SYNTAX     CounterBasedGauge64
	MAX-ACCESS read-only
	STATUS     current
	DESCRIPTION "Server connections"

	::={ psmModelServerConnections 1 }

psmModelServerConnectionsMax OBJECT-TYPE
	SYNTAX     CounterBasedGauge64
	MAX-ACCESS read-only
	STATUS     current
	DESCRIPTION "Server connections"

	::={ psmModelServerConnections 3 }

psmModelServerConnectionsLevelTable OBJECT-TYPE
	SYNTAX     SEQUENCE OF PsmModelServerConnectionsLevelEntry
	MAX-ACCESS not-accessible
	STATUS     current
	DESCRIPTION
	"Server connections"
	::={ psmModelServerConnections 4 }

psmModelServerConnectionsLevelEntry OBJECT-TYPE
	SYNTAX      PsmModelServerConnectionsLevelEntry
	MAX-ACCESS  not-accessible
	STATUS      current
	DESCRIPTION
	"Server connections"
	INDEX { psmModelServerConnectionsLevelName }
	::={ psmModelServerConnectionsLevelTable 1 }

PsmModelServerConnectionsLevelEntry ::=
	SEQUENCE {
		psmModelServerConnectionsLevelName DisplayString,
		psmModelServerConnectionsLevelVal  CounterBasedGauge64,
		psmModelServerConnectionsLevelMax  CounterBasedGauge64
	}

psmModelServerConnectionsLevelName OBJECT-TYPE
	SYNTAX      DisplayString
	MAX-ACCESS  not-accessible
	STATUS      current
	DESCRIPTION
	"Server connections"
	::={ psmModelServerConnectionsLevelEntry 1}

psmModelServerConnectionsLevelVal OBJECT-TYPE
	SYNTAX     CounterBasedGauge64
	MAX-ACCESS read-only
	STATUS     current
	DESCRIPTION
	"Server connections"
	::={ psmModelServerConnectionsLevelEntry 2 }

psmModelServerConnectionsLevelMax OBJECT-TYPE
	SYNTAX     CounterBasedGauge64
	MAX-ACCESS read-only
	STATUS     current
	DESCRIPTION
	"Server connections"
	::={ psmModelServerConnectionsLevelEntry 4 }

psmModelServerTotalConnections OBJECT IDENTIFIER ::= { psmModel 2 }

psmModelServerTotalConnectionsVal OBJECT-TYPE
	SYNTAX     Counter64
	MAX-ACCESS read-only
	STATUS     current
	DESCRIPTION "Server total connections"

	::={ psmModelServerTotalConnections 1 }

psmModelServerTotalConnectionsMom OBJECT-TYPE
	SYNTAX     CounterBasedGauge64
	MAX-ACCESS read-only
	STATUS     current
	DESCRIPTION "Server total connections"

	::={ psmModelServerTotalConnections 2 }

psmModelServerTotalConnectionsMax OBJECT-TYPE
	SYNTAX     CounterBasedGauge64
	MAX-ACCESS read-only
	STATUS     current
	DESCRIPTION "Server total connections"

	::={ psmModelServerTotalConnections 3 }

psmModelServerTotalConnectionsLevelTable OBJECT-TYPE
	SYNTAX     SEQUENCE OF PsmModelServerTotalConnectionsLevelEntry
	MAX-ACCESS not-accessible
	STATUS     current
	DESCRIPTION
	"Server total connections"
	::={ psmModelServerTotalConnections 4 }

psmModelServerTotalConnectionsLevelEntry OBJECT-TYPE
	SYNTAX      PsmModelServerTotalConnectionsLevelEntry
	MAX-ACCESS  not-accessible
	STATUS      current
	DESCRIPTION
	"Server total connections"
	INDEX { psmModelServerTotalConnectionsLevelName }
	::={ psmModelServerTotalConnectionsLevelTable 1 }

PsmModelServerTotalConnectionsLevelEntry ::=
	SEQUENCE {
		psmModelServerTotalConnectionsLevelName DisplayString,
		psmModelServerTotalConnectionsLevelVal  Counter64,
		psmModelServerTotalConnectionsLevelMom  CounterBasedGauge64,
		psmModelServerTotalConnectionsLevelMax  CounterBasedGauge64
	}

psmModelServerTotalConnectionsLevelName OBJECT-TYPE
	SYNTAX      DisplayString
	MAX-ACCESS  not-accessible
	STATUS      current
	DESCRIPTION
	"Server total connections"
	::={ psmModelServerTotalConnectionsLevelEntry 1}

psmModelServerTotalConnectionsLevelVal OBJECT-TYPE
	SYNTAX     Counter64
	MAX-ACCESS read-only
	STATUS     current
	DESCRIPTION
	"Server total connections"
	::={ psmModelServerTotalConnectionsLevelEntry 2 }

psmModelServerTotalConnectionsLevelMom OBJECT-TYPE
	SYNTAX     CounterBasedGauge64
	MAX-ACCESS read-only
	STATUS     current
	DESCRIPTION
	"Server total connections"
	::={ psmModelServerTotalConnectionsLevelEntry 3 }

psmModelServerTotalConnectionsLevelMax OBJECT-TYPE
	SYNTAX     CounterBasedGauge64
	MAX-ACCESS read-only
	STATUS     current
	DESCRIPTION
	"Server total connections"
	::={ psmModelServerTotalConnectionsLevelEntry 4 }

psmModelClientStateChanged OBJECT IDENTIFIER ::= { psmModel 3 }

psmModelClientStateChangedVal OBJECT-TYPE
	SYNTAX     DateAndTime
	MAX-ACCESS read-only
	STATUS     current
	DESCRIPTION "Client state changed"

	::={ psmModelClientStateChanged 1 }

psmModelClientStateChangedLevelTable OBJECT-TYPE
	SYNTAX     SEQUENCE OF PsmModelClientStateChangedLevelEntry
	MAX-ACCESS not-accessible
	STATUS     current
	DESCRIPTION
	"Client state changed"
	::={ psmModelClientStateChanged 4 }

psmModelClientStateChangedLevelEntry OBJECT-TYPE
	SYNTAX      PsmModelClientStateChangedLevelEntry
	MAX-ACCESS  not-accessible
	STATUS      current
	DESCRIPTION
	"Client state changed"
	INDEX { psmModelClientStateChangedLevelName }
	::={ psmModelClientStateChangedLevelTable 1 }

PsmModelClientStateChangedLevelEntry ::=
	SEQUENCE {
		psmModelClientStateChangedLevelName DisplayString,
		psmModelClientStateChangedLevelVal  DateAndTime
	}

psmModelClientStateChangedLevelName OBJECT-TYPE
	SYNTAX      DisplayString
	MAX-ACCESS  not-accessible
	STATUS      current
	DESCRIPTION
	"Client state changed"
	::={ psmModelClientStateChangedLevelEntry 1}

psmModelClientStateChangedLevelVal OBJECT-TYPE
	SYNTAX     DateAndTime
	MAX-ACCESS read-only
	STATUS     current
	DESCRIPTION
	"Client state changed"
	::={ psmModelClientStateChangedLevelEntry 2 }

psmModelClientReconnects OBJECT IDENTIFIER ::= { psmModel 4 }

psmModelClientReconnectsVal OBJECT-TYPE
	SYNTAX     Counter64
	MAX-ACCESS read-only
	STATUS     current
	DESCRIPTION "Client reconnects"

	::={ psmModelClientReconnects 1 }

psmModelClientReconnectsMom OBJECT-TYPE
	SYNTAX     CounterBasedGauge64
	MAX-ACCESS read-only
	STATUS     current
	DESCRIPTION "Client reconnects"

	::={ psmModelClientReconnects 2 }

psmModelClientReconnectsMax OBJECT-TYPE
	SYNTAX     CounterBasedGauge64
	MAX-ACCESS read-only
	STATUS     current
	DESCRIPTION "Client reconnects"

	::={ psmModelClientReconnects 3 }

psmModelClientReconnectsLevelTable OBJECT-TYPE
	SYNTAX     SEQUENCE OF PsmModelClientReconnectsLevelEntry
	MAX-ACCESS not-accessible
	STATUS     current
	DESCRIPTION
	"Client reconnects"
	::={ psmModelClientReconnects 4 }

psmModelClientReconnectsLevelEntry OBJECT-TYPE
	SYNTAX      PsmModelClientReconnectsLevelEntry
	MAX-ACCESS  not-accessible
	STATUS      current
	DESCRIPTION
	"Client reconnects"
	INDEX { psmModelClientReconnectsLevelName }
	::={ psmModelClientReconnectsLevelTable 1 }

PsmModelClientReconnectsLevelEntry ::=
	SEQUENCE {
		psmModelClientReconnectsLevelName DisplayString,
		psmModelClientReconnectsLevelVal  Counter64,
		psmModelClientReconnectsLevelMom  CounterBasedGauge64,
		psmModelClientReconnectsLevelMax  CounterBasedGauge64
	}

psmModelClientReconnectsLevelName OBJECT-TYPE
	SYNTAX      DisplayString
	MAX-ACCESS  not-accessible
	STATUS      current
	DESCRIPTION
	"Client reconnects"
	::={ psmModelClientReconnectsLevelEntry 1}

psmModelClientReconnectsLevelVal OBJECT-TYPE
	SYNTAX     Counter64
	MAX-ACCESS read-only
	STATUS     current
	DESCRIPTION
	"Client reconnects"
	::={ psmModelClientReconnectsLevelEntry 2 }

psmModelClientReconnectsLevelMom OBJECT-TYPE
	SYNTAX     CounterBasedGauge64
	MAX-ACCESS read-only
	STATUS     current
	DESCRIPTION
	"Client reconnects"
	::={ psmModelClientReconnectsLevelEntry 3 }

psmModelClientReconnectsLevelMax OBJECT-TYPE
	SYNTAX     CounterBasedGauge64
	MAX-ACCESS read-only
	STATUS     current
	DESCRIPTION
	"Client reconnects"
	::={ psmModelClientReconnectsLevelEntry 4 }

psmModelClientState OBJECT IDENTIFIER ::= { psmModel 5 }

psmModelClientStateVal OBJECT-TYPE
	SYNTAX     INTEGER {
		disconnected(0),
		connected(1),
		synchronizing(2),
		verifying(3),
		insync(4),
		draining(5)
	}
	MAX-ACCESS read-only
	STATUS     current
	DESCRIPTION "Client state"

	::={ psmModelClientState 1 }

psmModelClientStateLevelTable OBJECT-TYPE
	SYNTAX     SEQUENCE OF PsmModelClientStateLevelEntry
	MAX-ACCESS not-accessible
	STATUS     current
	DESCRIPTION
	"Client state"
	::={ psmModelClientState 4 }

psmModelClientStateLevelEntry OBJECT-TYPE
	SYNTAX      PsmModelClientStateLevelEntry
	MAX-ACCESS  not-accessible
	STATUS      current
	DESCRIPTION
	"Client state"
	INDEX { psmModelClientStateLevelName }
	::={ psmModelClientStateLevelTable 1 }

PsmModelClientStateLevelEntry ::=
	SEQUENCE {
		psmModelClientStateLevelName DisplayString,
		psmModelClientStateLevelVal  INTEGER
	}

psmModelClientStateLevelName OBJECT-TYPE
	SYNTAX      DisplayString
	MAX-ACCESS  not-accessible
	STATUS      current
	DESCRIPTION
	"Client state"
	::={ psmModelClientStateLevelEntry 1}

psmModelClientStateLevelVal OBJECT-TYPE
	SYNTAX     INTEGER {
		disconnected(0),
		connected(1),
		synchronizing(2),
		verifying(3),
		insync(4),
		draining(5)
	}
	MAX-ACCESS read-only
	STATUS     current
	DESCRIPTION
	"Client state"
	::={ psmModelClientStateLevelEntry 2 }

psmModelTableChanged OBJECT IDENTIFIER ::= { psmModel 6 }

psmModelTableChangedVal OBJECT-TYPE
	SYNTAX     DateAndTime
	MAX-ACCESS read-only
	STATUS     current
	DESCRIPTION "Table changed"

	::={ psmModelTableChanged 1 }

psmModelTableChangedLevelTable OBJECT-TYPE
	SYNTAX     SEQUENCE OF PsmModelTableChangedLevelEntry
	MAX-ACCESS not-accessible
	STATUS     current
	DESCRIPTION
	"Table changed"
	::={ psmModelTableChanged 4 }

psmModelTableChangedLevelEntry OBJECT-TYPE
	SYNTAX      PsmModelTableChangedLevelEntry
	MAX-ACCESS  not-accessible
	STATUS      current
	DESCRIPTION
	"Table changed"
	INDEX { psmModelTableChangedLevelName }
	::={ psmModelTableChangedLevelTable 1 }

PsmModelTableChangedLevelEntry ::=
	SEQUENCE {
		psmModelTableChangedLevelName DisplayString,
		psmModelTableChangedLevelVal  DateAndTime
	}

psmModelTableChangedLevelName OBJECT-TYPE
	SYNTAX      DisplayString
	MAX-ACCESS  not-accessible
	STATUS      current
	DESCRIPTION
	"Table changed"
	::={ psmModelTableChangedLevelEntry 1}

psmModelTableChangedLevelVal OBJECT-TYPE
	SYNTAX     DateAndTime
	MAX-ACCESS read-only
	STATUS     current
	DESCRIPTION
	"Table changed"
	::={ psmModelTableChangedLevelEntry 2 }

psmModelTableSize OBJECT IDENTIFIER ::= { psmModel 7 }

psmModelTableSizeVal OBJECT-TYPE
	SYNTAX     CounterBasedGauge64
	MAX-ACCESS read-only
	STATUS     current
	DESCRIPTION "Table size"

	::={ psmModelTableSize 1 }

psmModelTableSizeMax OBJECT-TYPE
	SYNTAX     CounterBasedGauge64
	MAX-ACCESS read-only
	STATUS     current
	DESCRIPTION "Table size"

	::={ psmModelTableSize 3 }

psmModelTableSizeLevelTable OBJECT-TYPE
	SYNTAX     SEQUENCE OF PsmModelTableSizeLevelEntry
	MAX-ACCESS not-accessible
	STATUS     current
	DESCRIPTION
	"Table size"
	::={ psmModelTableSize 4 }

psmModelTableSizeLevelEntry OBJECT-TYPE
	SYNTAX      PsmModelTableSizeLevelEntry
	MAX-ACCESS  not-accessible
	STATUS      current
	DESCRIPTION
	"Table size"
	INDEX { psmModelTableSizeLevelName }
	::={ psmModelTableSizeLevelTable 1 }

PsmModelTableSizeLevelEntry ::=
	SEQUENCE {
		psmModelTableSizeLevelName DisplayString,
		psmModelTableSizeLevelVal  CounterBasedGauge64,
		psmModelTableSizeLevelMax  CounterBasedGauge64
	}

psmModelTableSizeLevelName OBJECT-TYPE
	SYNTAX      DisplayString
	MAX-ACCESS  not-accessible
	STATUS      current
	DESCRIPTION
	"Table size"
	::={ psmModelTableSizeLevelEntry 1}

psmModelTableSizeLevelVal OBJECT-TYPE
	SYNTAX     CounterBasedGauge64
	MAX-ACCESS read-only
	STATUS     current
	DESCRIPTION
	"Table size"
	::={ psmModelTableSizeLevelEntry 2 }

psmModelTableSizeLevelMax OBJECT-TYPE
	SYNTAX     CounterBasedGauge64
	MAX-ACCESS read-only
	STATUS     current
	DESCRIPTION
	"Table size"
	::={ psmModelTableSizeLevelEntry 4 }

psmModelObjectCounters OBJECT IDENTIFIER ::= { psmModel 8 }

psmModelObjectCountersVal OBJECT-TYPE
	SYNTAX     Counter64
	MAX-ACCESS read-only
	STATUS     current
	DESCRIPTION "Object counters"

	::={ psmModelObjectCounters 1 }

psmModelObjectCountersMom OBJECT-TYPE
	SYNTAX     CounterBasedGauge64
	MAX-ACCESS read-only
	STATUS     current
	DESCRIPTION "Object counters"

	::={ psmModelObjectCounters 2 }

psmModelObjectCountersMax OBJECT-TYPE
	SYNTAX     CounterBasedGauge64
	MAX-ACCESS read-only
	STATUS     current
	DESCRIPTION "Object counters"

	::={ psmModelObjectCounters 3 }

psmModelObjectCountersLevelTable OBJECT-TYPE
	SYNTAX     SEQUENCE OF PsmModelObjectCountersLevelEntry
	MAX-ACCESS not-accessible
	STATUS     current
	DESCRIPTION
	"Object counters"
	::={ psmModelObjectCounters 4 }

psmModelObjectCountersLevelEntry OBJECT-TYPE
	SYNTAX      PsmModelObjectCountersLevelEntry
	MAX-ACCESS  not-accessible
	STATUS      current
	DESCRIPTION
	"Object counters"
	INDEX { psmModelObjectCountersLevelName }
	::={ psmModelObjectCountersLevelTable 1 }

PsmModelObjectCountersLevelEntry ::=
	SEQUENCE {
		psmModelObjectCountersLevelName DisplayString,
		psmModelObjectCountersLevelVal  Counter64,
		psmModelObjectCountersLevelMom  CounterBasedGauge64,
		psmModelObjectCountersLevelMax  CounterBasedGauge64
	}

psmModelObjectCountersLevelName OBJECT-TYPE
	SYNTAX      DisplayString
	MAX-ACCESS  not-accessible
	STATUS      current
	DESCRIPTION
	"Object counters"
	::={ psmModelObjectCountersLevelEntry 1}

psmModelObjectCountersLevelVal OBJECT-TYPE
	SYNTAX     Counter64
	MAX-ACCESS read-only
	STATUS     current
	DESCRIPTION
	"Object counters"
	::={ psmModelObjectCountersLevelEntry 2 }

psmModelObjectCountersLevelMom OBJECT-TYPE
	SYNTAX     CounterBasedGauge64
	MAX-ACCESS read-only
	STATUS     current
	DESCRIPTION
	"Object counters"
	::={ psmModelObjectCountersLevelEntry 3 }

psmModelObjectCountersLevelMax OBJECT-TYPE
	SYNTAX     CounterBasedGauge64
	MAX-ACCESS read-only
	STATUS     current
	DESCRIPTION
	"Object counters"
	::={ psmModelObjectCountersLevelEntry 4 }

psmModelIndexSize OBJECT IDENTIFIER ::= { psmModel 9 }

psmModelIndexSizeVal OBJECT-TYPE
	SYNTAX     Counter64
	MAX-ACCESS read-only
	STATUS     current
	DESCRIPTION "Index size"

	::={ psmModelIndexSize 1 }

psmModelIndexSizeMom OBJECT-TYPE
	SYNTAX     CounterBasedGauge64
	MAX-ACCESS read-only
	STATUS     current
	DESCRIPTION "Index size"

	::={ psmModelIndexSize 2 }

psmModelIndexSizeMax OBJECT-TYPE
	SYNTAX     CounterBasedGauge64
	MAX-ACCESS read-only
	STATUS     current
	DESCRIPTION "Index size"

	::={ psmModelIndexSize 3 }

psmModelIndexSizeLevelTable OBJECT-TYPE
	SYNTAX     SEQUENCE OF PsmModelIndexSizeLevelEntry
	MAX-ACCESS not-accessible
	STATUS     current
	DESCRIPTION
	"Index size"
	::={ psmModelIndexSize 4 }

psmModelIndexSizeLevelEntry OBJECT-TYPE
	SYNTAX      PsmModelIndexSizeLevelEntry
	MAX-ACCESS  not-accessible
	STATUS      current
	DESCRIPTION
	"Index size"
	INDEX { psmModelIndexSizeLevelName }
	::={ psmModelIndexSizeLevelTable 1 }

PsmModelIndexSizeLevelEntry ::=
	SEQUENCE {
		psmModelIndexSizeLevelName DisplayString,
		psmModelIndexSizeLevelVal  Counter64,
		psmModelIndexSizeLevelMom  CounterBasedGauge64,
		psmModelIndexSizeLevelMax  CounterBasedGauge64
	}

psmModelIndexSizeLevelName OBJECT-TYPE
	SYNTAX      DisplayString
	MAX-ACCESS  not-accessible
	STATUS      current
	DESCRIPTION
	"Index size"
	::={ psmModelIndexSizeLevelEntry 1}

psmModelIndexSizeLevelVal OBJECT-TYPE
	SYNTAX     Counter64
	MAX-ACCESS read-only
	STATUS     current
	DESCRIPTION
	"Index size"
	::={ psmModelIndexSizeLevelEntry 2 }

psmModelIndexSizeLevelMom OBJECT-TYPE
	SYNTAX     CounterBasedGauge64
	MAX-ACCESS read-only
	STATUS     current
	DESCRIPTION
	"Index size"
	::={ psmModelIndexSizeLevelEntry 3 }

psmModelIndexSizeLevelMax OBJECT-TYPE
	SYNTAX     CounterBasedGauge64
	MAX-ACCESS read-only
	STATUS     current
	DESCRIPTION
	"Index size"
	::={ psmModelIndexSizeLevelEntry 4 }

psmModelObjectCount OBJECT IDENTIFIER ::= { psmModel 10 }

psmModelObjectCountVal OBJECT-TYPE
	SYNTAX     Counter64
	MAX-ACCESS read-only
	STATUS     current
	DESCRIPTION "Object count"

	::={ psmModelObjectCount 1 }

psmModelObjectCountMom OBJECT-TYPE
	SYNTAX     CounterBasedGauge64
	MAX-ACCESS read-only
	STATUS     current
	DESCRIPTION "Object count"

	::={ psmModelObjectCount 2 }

psmModelObjectCountMax OBJECT-TYPE
	SYNTAX     CounterBasedGauge64
	MAX-ACCESS read-only
	STATUS     current
	DESCRIPTION "Object count"

	::={ psmModelObjectCount 3 }

psmModelObjectCountLevelTable OBJECT-TYPE
	SYNTAX     SEQUENCE OF PsmModelObjectCountLevelEntry
	MAX-ACCESS not-accessible
	STATUS     current
	DESCRIPTION
	"Object count"
	::={ psmModelObjectCount 4 }

psmModelObjectCountLevelEntry OBJECT-TYPE
	SYNTAX      PsmModelObjectCountLevelEntry
	MAX-ACCESS  not-accessible
	STATUS      current
	DESCRIPTION
	"Object count"
	INDEX { psmModelObjectCountLevelName }
	::={ psmModelObjectCountLevelTable 1 }

PsmModelObjectCountLevelEntry ::=
	SEQUENCE {
		psmModelObjectCountLevelName DisplayString,
		psmModelObjectCountLevelVal  Counter64,
		psmModelObjectCountLevelMom  CounterBasedGauge64,
		psmModelObjectCountLevelMax  CounterBasedGauge64
	}

psmModelObjectCountLevelName OBJECT-TYPE
	SYNTAX      DisplayString
	MAX-ACCESS  not-accessible
	STATUS      current
	DESCRIPTION
	"Object count"
	::={ psmModelObjectCountLevelEntry 1}

psmModelObjectCountLevelVal OBJECT-TYPE
	SYNTAX     Counter64
	MAX-ACCESS read-only
	STATUS     current
	DESCRIPTION
	"Object count"
	::={ psmModelObjectCountLevelEntry 2 }

psmModelObjectCountLevelMom OBJECT-TYPE
	SYNTAX     CounterBasedGauge64
	MAX-ACCESS read-only
	STATUS     current
	DESCRIPTION
	"Object count"
	::={ psmModelObjectCountLevelEntry 3 }

psmModelObjectCountLevelMax OBJECT-TYPE
	SYNTAX     CounterBasedGauge64
	MAX-ACCESS read-only
	STATUS     current
	DESCRIPTION
	"Object count"
	::={ psmModelObjectCountLevelEntry 4 }

psmModelLifetimeCountLess15m OBJECT IDENTIFIER ::= { psmModel 11 }

psmModelLifetimeCountLess15mVal OBJECT-TYPE
	SYNTAX     Counter64
	MAX-ACCESS read-only
	STATUS     current
	DESCRIPTION "Lifetime count <= 15m"

	::={ psmModelLifetimeCountLess15m 1 }

psmModelLifetimeCountLess15mMom OBJECT-TYPE
	SYNTAX     CounterBasedGauge64
	MAX-ACCESS read-only
	STATUS     current
	DESCRIPTION "Lifetime count <= 15m"

	::={ psmModelLifetimeCountLess15m 2 }

psmModelLifetimeCountLess15mMax OBJECT-TYPE
	SYNTAX     CounterBasedGauge64
	MAX-ACCESS read-only
	STATUS     current
	DESCRIPTION "Lifetime count <= 15m"

	::={ psmModelLifetimeCountLess15m 3 }

psmModelLifetimeCountLess15mLevelTable OBJECT-TYPE
	SYNTAX     SEQUENCE OF PsmModelLifetimeCountLess15mLevelEntry
	MAX-ACCESS not-accessible
	STATUS     current
	DESCRIPTION
	"Lifetime count <= 15m"
	::={ psmModelLifetimeCountLess15m 4 }

psmModelLifetimeCountLess15mLevelEntry OBJECT-TYPE
	SYNTAX      PsmModelLifetimeCountLess15mLevelEntry
	MAX-ACCESS  not-accessible
	STATUS      current
	DESCRIPTION
	"Lifetime count <= 15m"
	INDEX { psmModelLifetimeCountLess15mLevelName }
	::={ psmModelLifetimeCountLess15mLevelTable 1 }

PsmModelLifetimeCountLess15mLevelEntry ::=
	SEQUENCE {
		psmModelLifetimeCountLess15mLevelName DisplayString,
		psmModelLifetimeCountLess15mLevelVal  Counter64,
		psmModelLifetimeCountLess15mLevelMom  CounterBasedGauge64,
		psmModelLifetimeCountLess15mLevelMax  CounterBasedGauge64
	}

psmModelLifetimeCountLess15mLevelName OBJECT-TYPE
	SYNTAX      DisplayString
	MAX-ACCESS  not-accessible
	STATUS      current
	DESCRIPTION
	"Lifetime count <= 15m"
	::={ psmModelLifetimeCountLess15mLevelEntry 1}

psmModelLifetimeCountLess15mLevelVal OBJECT-TYPE
	SYNTAX     Counter64
	MAX-ACCESS read-only
	STATUS     current
	DESCRIPTION
	"Lifetime count <= 15m"
	::={ psmModelLifetimeCountLess15mLevelEntry 2 }

psmModelLifetimeCountLess15mLevelMom OBJECT-TYPE
	SYNTAX     CounterBasedGauge64
	MAX-ACCESS read-only
	STATUS     current
	DESCRIPTION
	"Lifetime count <= 15m"
	::={ psmModelLifetimeCountLess15mLevelEntry 3 }

psmModelLifetimeCountLess15mLevelMax OBJECT-TYPE
	SYNTAX     CounterBasedGauge64
	MAX-ACCESS read-only
	STATUS     current
	DESCRIPTION
	"Lifetime count <= 15m"
	::={ psmModelLifetimeCountLess15mLevelEntry 4 }

psmModelLifetimeCountLess15s OBJECT IDENTIFIER ::= { psmModel 12 }

psmModelLifetimeCountLess15sVal OBJECT-TYPE
	SYNTAX     Counter64
	MAX-ACCESS read-only
	STATUS     current
	DESCRIPTION "Lifetime count <= 15s"

	::={ psmModelLifetimeCountLess15s 1 }

psmModelLifetimeCountLess15sMom OBJECT-TYPE
	SYNTAX     CounterBasedGauge64
	MAX-ACCESS read-only
	STATUS     current
	DESCRIPTION "Lifetime count <= 15s"

	::={ psmModelLifetimeCountLess15s 2 }

psmModelLifetimeCountLess15sMax OBJECT-TYPE
	SYNTAX     CounterBasedGauge64
	MAX-ACCESS read-only
	STATUS     current
	DESCRIPTION "Lifetime count <= 15s"

	::={ psmModelLifetimeCountLess15s 3 }

psmModelLifetimeCountLess15sLevelTable OBJECT-TYPE
	SYNTAX     SEQUENCE OF PsmModelLifetimeCountLess15sLevelEntry
	MAX-ACCESS not-accessible
	STATUS     current
	DESCRIPTION
	"Lifetime count <= 15s"
	::={ psmModelLifetimeCountLess15s 4 }

psmModelLifetimeCountLess15sLevelEntry OBJECT-TYPE
	SYNTAX      PsmModelLifetimeCountLess15sLevelEntry
	MAX-ACCESS  not-accessible
	STATUS      current
	DESCRIPTION
	"Lifetime count <= 15s"
	INDEX { psmModelLifetimeCountLess15sLevelName }
	::={ psmModelLifetimeCountLess15sLevelTable 1 }

PsmModelLifetimeCountLess15sLevelEntry ::=
	SEQUENCE {
		psmModelLifetimeCountLess15sLevelName DisplayString,
		psmModelLifetimeCountLess15sLevelVal  Counter64,
		psmModelLifetimeCountLess15sLevelMom  CounterBasedGauge64,
		psmModelLifetimeCountLess15sLevelMax  CounterBasedGauge64
	}

psmModelLifetimeCountLess15sLevelName OBJECT-TYPE
	SYNTAX      DisplayString
	MAX-ACCESS  not-accessible
	STATUS      current
	DESCRIPTION
	"Lifetime count <= 15s"
	::={ psmModelLifetimeCountLess15sLevelEntry 1}

psmModelLifetimeCountLess15sLevelVal OBJECT-TYPE
	SYNTAX     Counter64
	MAX-ACCESS read-only
	STATUS     current
	DESCRIPTION
	"Lifetime count <= 15s"
	::={ psmModelLifetimeCountLess15sLevelEntry 2 }

psmModelLifetimeCountLess15sLevelMom OBJECT-TYPE
	SYNTAX     CounterBasedGauge64
	MAX-ACCESS read-only
	STATUS     current
	DESCRIPTION
	"Lifetime count <= 15s"
	::={ psmModelLifetimeCountLess15sLevelEntry 3 }

psmModelLifetimeCountLess15sLevelMax OBJECT-TYPE
	SYNTAX     CounterBasedGauge64
	MAX-ACCESS read-only
	STATUS     current
	DESCRIPTION
	"Lifetime count <= 15s"
	::={ psmModelLifetimeCountLess15sLevelEntry 4 }

psmModelLifetimeCountLess1d OBJECT IDENTIFIER ::= { psmModel 13 }

psmModelLifetimeCountLess1dVal OBJECT-TYPE
	SYNTAX     Counter64
	MAX-ACCESS read-only
	STATUS     current
	DESCRIPTION "Lifetime count <= 1d"

	::={ psmModelLifetimeCountLess1d 1 }

psmModelLifetimeCountLess1dMom OBJECT-TYPE
	SYNTAX     CounterBasedGauge64
	MAX-ACCESS read-only
	STATUS     current
	DESCRIPTION "Lifetime count <= 1d"

	::={ psmModelLifetimeCountLess1d 2 }

psmModelLifetimeCountLess1dMax OBJECT-TYPE
	SYNTAX     CounterBasedGauge64
	MAX-ACCESS read-only
	STATUS     current
	DESCRIPTION "Lifetime count <= 1d"

	::={ psmModelLifetimeCountLess1d 3 }

psmModelLifetimeCountLess1dLevelTable OBJECT-TYPE
	SYNTAX     SEQUENCE OF PsmModelLifetimeCountLess1dLevelEntry
	MAX-ACCESS not-accessible
	STATUS     current
	DESCRIPTION
	"Lifetime count <= 1d"
	::={ psmModelLifetimeCountLess1d 4 }

psmModelLifetimeCountLess1dLevelEntry OBJECT-TYPE
	SYNTAX      PsmModelLifetimeCountLess1dLevelEntry
	MAX-ACCESS  not-accessible
	STATUS      current
	DESCRIPTION
	"Lifetime count <= 1d"
	INDEX { psmModelLifetimeCountLess1dLevelName }
	::={ psmModelLifetimeCountLess1dLevelTable 1 }

PsmModelLifetimeCountLess1dLevelEntry ::=
	SEQUENCE {
		psmModelLifetimeCountLess1dLevelName DisplayString,
		psmModelLifetimeCountLess1dLevelVal  Counter64,
		psmModelLifetimeCountLess1dLevelMom  CounterBasedGauge64,
		psmModelLifetimeCountLess1dLevelMax  CounterBasedGauge64
	}

psmModelLifetimeCountLess1dLevelName OBJECT-TYPE
	SYNTAX      DisplayString
	MAX-ACCESS  not-accessible
	STATUS      current
	DESCRIPTION
	"Lifetime count <= 1d"
	::={ psmModelLifetimeCountLess1dLevelEntry 1}

psmModelLifetimeCountLess1dLevelVal OBJECT-TYPE
	SYNTAX     Counter64
	MAX-ACCESS read-only
	STATUS     current
	DESCRIPTION
	"Lifetime count <= 1d"
	::={ psmModelLifetimeCountLess1dLevelEntry 2 }

psmModelLifetimeCountLess1dLevelMom OBJECT-TYPE
	SYNTAX     CounterBasedGauge64
	MAX-ACCESS read-only
	STATUS     current
	DESCRIPTION
	"Lifetime count <= 1d"
	::={ psmModelLifetimeCountLess1dLevelEntry 3 }

psmModelLifetimeCountLess1dLevelMax OBJECT-TYPE
	SYNTAX     CounterBasedGauge64
	MAX-ACCESS read-only
	STATUS     current
	DESCRIPTION
	"Lifetime count <= 1d"
	::={ psmModelLifetimeCountLess1dLevelEntry 4 }

psmModelLifetimeCountMore1d OBJECT IDENTIFIER ::= { psmModel 14 }

psmModelLifetimeCountMore1dVal OBJECT-TYPE
	SYNTAX     Counter64
	MAX-ACCESS read-only
	STATUS     current
	DESCRIPTION "Lifetime count > 1d"

	::={ psmModelLifetimeCountMore1d 1 }

psmModelLifetimeCountMore1dMom OBJECT-TYPE
	SYNTAX     CounterBasedGauge64
	MAX-ACCESS read-only
	STATUS     current
	DESCRIPTION "Lifetime count > 1d"

	::={ psmModelLifetimeCountMore1d 2 }

psmModelLifetimeCountMore1dMax OBJECT-TYPE
	SYNTAX     CounterBasedGauge64
	MAX-ACCESS read-only
	STATUS     current
	DESCRIPTION "Lifetime count > 1d"

	::={ psmModelLifetimeCountMore1d 3 }

psmModelLifetimeCountMore1dLevelTable OBJECT-TYPE
	SYNTAX     SEQUENCE OF PsmModelLifetimeCountMore1dLevelEntry
	MAX-ACCESS not-accessible
	STATUS     current
	DESCRIPTION
	"Lifetime count > 1d"
	::={ psmModelLifetimeCountMore1d 4 }

psmModelLifetimeCountMore1dLevelEntry OBJECT-TYPE
	SYNTAX      PsmModelLifetimeCountMore1dLevelEntry
	MAX-ACCESS  not-accessible
	STATUS      current
	DESCRIPTION
	"Lifetime count > 1d"
	INDEX { psmModelLifetimeCountMore1dLevelName }
	::={ psmModelLifetimeCountMore1dLevelTable 1 }

PsmModelLifetimeCountMore1dLevelEntry ::=
	SEQUENCE {
		psmModelLifetimeCountMore1dLevelName DisplayString,
		psmModelLifetimeCountMore1dLevelVal  Counter64,
		psmModelLifetimeCountMore1dLevelMom  CounterBasedGauge64,
		psmModelLifetimeCountMore1dLevelMax  CounterBasedGauge64
	}

psmModelLifetimeCountMore1dLevelName OBJECT-TYPE
	SYNTAX      DisplayString
	MAX-ACCESS  not-accessible
	STATUS      current
	DESCRIPTION
	"Lifetime count > 1d"
	::={ psmModelLifetimeCountMore1dLevelEntry 1}

psmModelLifetimeCountMore1dLevelVal OBJECT-TYPE
	SYNTAX     Counter64
	MAX-ACCESS read-only
	STATUS     current
	DESCRIPTION
	"Lifetime count > 1d"
	::={ psmModelLifetimeCountMore1dLevelEntry 2 }

psmModelLifetimeCountMore1dLevelMom OBJECT-TYPE
	SYNTAX     CounterBasedGauge64
	MAX-ACCESS read-only
	STATUS     current
	DESCRIPTION
	"Lifetime count > 1d"
	::={ psmModelLifetimeCountMore1dLevelEntry 3 }

psmModelLifetimeCountMore1dLevelMax OBJECT-TYPE
	SYNTAX     CounterBasedGauge64
	MAX-ACCESS read-only
	STATUS     current
	DESCRIPTION
	"Lifetime count > 1d"
	::={ psmModelLifetimeCountMore1dLevelEntry 4 }

psmModelLifetimeCountLess1h OBJECT IDENTIFIER ::= { psmModel 15 }

psmModelLifetimeCountLess1hVal OBJECT-TYPE
	SYNTAX     Counter64
	MAX-ACCESS read-only
	STATUS     current
	DESCRIPTION "Lifetime count <= 1h"

	::={ psmModelLifetimeCountLess1h 1 }

psmModelLifetimeCountLess1hMom OBJECT-TYPE
	SYNTAX     CounterBasedGauge64
	MAX-ACCESS read-only
	STATUS     current
	DESCRIPTION "Lifetime count <= 1h"

	::={ psmModelLifetimeCountLess1h 2 }

psmModelLifetimeCountLess1hMax OBJECT-TYPE
	SYNTAX     CounterBasedGauge64
	MAX-ACCESS read-only
	STATUS     current
	DESCRIPTION "Lifetime count <= 1h"

	::={ psmModelLifetimeCountLess1h 3 }

psmModelLifetimeCountLess1hLevelTable OBJECT-TYPE
	SYNTAX     SEQUENCE OF PsmModelLifetimeCountLess1hLevelEntry
	MAX-ACCESS not-accessible
	STATUS     current
	DESCRIPTION
	"Lifetime count <= 1h"
	::={ psmModelLifetimeCountLess1h 4 }

psmModelLifetimeCountLess1hLevelEntry OBJECT-TYPE
	SYNTAX      PsmModelLifetimeCountLess1hLevelEntry
	MAX-ACCESS  not-accessible
	STATUS      current
	DESCRIPTION
	"Lifetime count <= 1h"
	INDEX { psmModelLifetimeCountLess1hLevelName }
	::={ psmModelLifetimeCountLess1hLevelTable 1 }

PsmModelLifetimeCountLess1hLevelEntry ::=
	SEQUENCE {
		psmModelLifetimeCountLess1hLevelName DisplayString,
		psmModelLifetimeCountLess1hLevelVal  Counter64,
		psmModelLifetimeCountLess1hLevelMom  CounterBasedGauge64,
		psmModelLifetimeCountLess1hLevelMax  CounterBasedGauge64
	}

psmModelLifetimeCountLess1hLevelName OBJECT-TYPE
	SYNTAX      DisplayString
	MAX-ACCESS  not-accessible
	STATUS      current
	DESCRIPTION
	"Lifetime count <= 1h"
	::={ psmModelLifetimeCountLess1hLevelEntry 1}

psmModelLifetimeCountLess1hLevelVal OBJECT-TYPE
	SYNTAX     Counter64
	MAX-ACCESS read-only
	STATUS     current
	DESCRIPTION
	"Lifetime count <= 1h"
	::={ psmModelLifetimeCountLess1hLevelEntry 2 }

psmModelLifetimeCountLess1hLevelMom OBJECT-TYPE
	SYNTAX     CounterBasedGauge64
	MAX-ACCESS read-only
	STATUS     current
	DESCRIPTION
	"Lifetime count <= 1h"
	::={ psmModelLifetimeCountLess1hLevelEntry 3 }

psmModelLifetimeCountLess1hLevelMax OBJECT-TYPE
	SYNTAX     CounterBasedGauge64
	MAX-ACCESS read-only
	STATUS     current
	DESCRIPTION
	"Lifetime count <= 1h"
	::={ psmModelLifetimeCountLess1hLevelEntry 4 }

psmModelLifetimeCountLess1m OBJECT IDENTIFIER ::= { psmModel 16 }

psmModelLifetimeCountLess1mVal OBJECT-TYPE
	SYNTAX     Counter64
	MAX-ACCESS read-only
	STATUS     current
	DESCRIPTION "Lifetime count <= 1m"

	::={ psmModelLifetimeCountLess1m 1 }

psmModelLifetimeCountLess1mMom OBJECT-TYPE
	SYNTAX     CounterBasedGauge64
	MAX-ACCESS read-only
	STATUS     current
	DESCRIPTION "Lifetime count <= 1m"

	::={ psmModelLifetimeCountLess1m 2 }

psmModelLifetimeCountLess1mMax OBJECT-TYPE
	SYNTAX     CounterBasedGauge64
	MAX-ACCESS read-only
	STATUS     current
	DESCRIPTION "Lifetime count <= 1m"

	::={ psmModelLifetimeCountLess1m 3 }

psmModelLifetimeCountLess1mLevelTable OBJECT-TYPE
	SYNTAX     SEQUENCE OF PsmModelLifetimeCountLess1mLevelEntry
	MAX-ACCESS not-accessible
	STATUS     current
	DESCRIPTION
	"Lifetime count <= 1m"
	::={ psmModelLifetimeCountLess1m 4 }

psmModelLifetimeCountLess1mLevelEntry OBJECT-TYPE
	SYNTAX      PsmModelLifetimeCountLess1mLevelEntry
	MAX-ACCESS  not-accessible
	STATUS      current
	DESCRIPTION
	"Lifetime count <= 1m"
	INDEX { psmModelLifetimeCountLess1mLevelName }
	::={ psmModelLifetimeCountLess1mLevelTable 1 }

PsmModelLifetimeCountLess1mLevelEntry ::=
	SEQUENCE {
		psmModelLifetimeCountLess1mLevelName DisplayString,
		psmModelLifetimeCountLess1mLevelVal  Counter64,
		psmModelLifetimeCountLess1mLevelMom  CounterBasedGauge64,
		psmModelLifetimeCountLess1mLevelMax  CounterBasedGauge64
	}

psmModelLifetimeCountLess1mLevelName OBJECT-TYPE
	SYNTAX      DisplayString
	MAX-ACCESS  not-accessible
	STATUS      current
	DESCRIPTION
	"Lifetime count <= 1m"
	::={ psmModelLifetimeCountLess1mLevelEntry 1}

psmModelLifetimeCountLess1mLevelVal OBJECT-TYPE
	SYNTAX     Counter64
	MAX-ACCESS read-only
	STATUS     current
	DESCRIPTION
	"Lifetime count <= 1m"
	::={ psmModelLifetimeCountLess1mLevelEntry 2 }

psmModelLifetimeCountLess1mLevelMom OBJECT-TYPE
	SYNTAX     CounterBasedGauge64
	MAX-ACCESS read-only
	STATUS     current
	DESCRIPTION
	"Lifetime count <= 1m"
	::={ psmModelLifetimeCountLess1mLevelEntry 3 }

psmModelLifetimeCountLess1mLevelMax OBJECT-TYPE
	SYNTAX     CounterBasedGauge64
	MAX-ACCESS read-only
	STATUS     current
	DESCRIPTION
	"Lifetime count <= 1m"
	::={ psmModelLifetimeCountLess1mLevelEntry 4 }

psmModelLifetimeCountLess4m OBJECT IDENTIFIER ::= { psmModel 17 }

psmModelLifetimeCountLess4mVal OBJECT-TYPE
	SYNTAX     Counter64
	MAX-ACCESS read-only
	STATUS     current
	DESCRIPTION "Lifetime count <= 4m"

	::={ psmModelLifetimeCountLess4m 1 }

psmModelLifetimeCountLess4mMom OBJECT-TYPE
	SYNTAX     CounterBasedGauge64
	MAX-ACCESS read-only
	STATUS     current
	DESCRIPTION "Lifetime count <= 4m"

	::={ psmModelLifetimeCountLess4m 2 }

psmModelLifetimeCountLess4mMax OBJECT-TYPE
	SYNTAX     CounterBasedGauge64
	MAX-ACCESS read-only
	STATUS     current
	DESCRIPTION "Lifetime count <= 4m"

	::={ psmModelLifetimeCountLess4m 3 }

psmModelLifetimeCountLess4mLevelTable OBJECT-TYPE
	SYNTAX     SEQUENCE OF PsmModelLifetimeCountLess4mLevelEntry
	MAX-ACCESS not-accessible
	STATUS     current
	DESCRIPTION
	"Lifetime count <= 4m"
	::={ psmModelLifetimeCountLess4m 4 }

psmModelLifetimeCountLess4mLevelEntry OBJECT-TYPE
	SYNTAX      PsmModelLifetimeCountLess4mLevelEntry
	MAX-ACCESS  not-accessible
	STATUS      current
	DESCRIPTION
	"Lifetime count <= 4m"
	INDEX { psmModelLifetimeCountLess4mLevelName }
	::={ psmModelLifetimeCountLess4mLevelTable 1 }

PsmModelLifetimeCountLess4mLevelEntry ::=
	SEQUENCE {
		psmModelLifetimeCountLess4mLevelName DisplayString,
		psmModelLifetimeCountLess4mLevelVal  Counter64,
		psmModelLifetimeCountLess4mLevelMom  CounterBasedGauge64,
		psmModelLifetimeCountLess4mLevelMax  CounterBasedGauge64
	}

psmModelLifetimeCountLess4mLevelName OBJECT-TYPE
	SYNTAX      DisplayString
	MAX-ACCESS  not-accessible
	STATUS      current
	DESCRIPTION
	"Lifetime count <= 4m"
	::={ psmModelLifetimeCountLess4mLevelEntry 1}

psmModelLifetimeCountLess4mLevelVal OBJECT-TYPE
	SYNTAX     Counter64
	MAX-ACCESS read-only
	STATUS     current
	DESCRIPTION
	"Lifetime count <= 4m"
	::={ psmModelLifetimeCountLess4mLevelEntry 2 }

psmModelLifetimeCountLess4mLevelMom OBJECT-TYPE
	SYNTAX     CounterBasedGauge64
	MAX-ACCESS read-only
	STATUS     current
	DESCRIPTION
	"Lifetime count <= 4m"
	::={ psmModelLifetimeCountLess4mLevelEntry 3 }

psmModelLifetimeCountLess4mLevelMax OBJECT-TYPE
	SYNTAX     CounterBasedGauge64
	MAX-ACCESS read-only
	STATUS     current
	DESCRIPTION
	"Lifetime count <= 4m"
	::={ psmModelLifetimeCountLess4mLevelEntry 4 }

psmModelLifetimeCountLess6h OBJECT IDENTIFIER ::= { psmModel 18 }

psmModelLifetimeCountLess6hVal OBJECT-TYPE
	SYNTAX     Counter64
	MAX-ACCESS read-only
	STATUS     current
	DESCRIPTION "Lifetime count <= 6h"

	::={ psmModelLifetimeCountLess6h 1 }

psmModelLifetimeCountLess6hMom OBJECT-TYPE
	SYNTAX     CounterBasedGauge64
	MAX-ACCESS read-only
	STATUS     current
	DESCRIPTION "Lifetime count <= 6h"

	::={ psmModelLifetimeCountLess6h 2 }

psmModelLifetimeCountLess6hMax OBJECT-TYPE
	SYNTAX     CounterBasedGauge64
	MAX-ACCESS read-only
	STATUS     current
	DESCRIPTION "Lifetime count <= 6h"

	::={ psmModelLifetimeCountLess6h 3 }

psmModelLifetimeCountLess6hLevelTable OBJECT-TYPE
	SYNTAX     SEQUENCE OF PsmModelLifetimeCountLess6hLevelEntry
	MAX-ACCESS not-accessible
	STATUS     current
	DESCRIPTION
	"Lifetime count <= 6h"
	::={ psmModelLifetimeCountLess6h 4 }

psmModelLifetimeCountLess6hLevelEntry OBJECT-TYPE
	SYNTAX      PsmModelLifetimeCountLess6hLevelEntry
	MAX-ACCESS  not-accessible
	STATUS      current
	DESCRIPTION
	"Lifetime count <= 6h"
	INDEX { psmModelLifetimeCountLess6hLevelName }
	::={ psmModelLifetimeCountLess6hLevelTable 1 }

PsmModelLifetimeCountLess6hLevelEntry ::=
	SEQUENCE {
		psmModelLifetimeCountLess6hLevelName DisplayString,
		psmModelLifetimeCountLess6hLevelVal  Counter64,
		psmModelLifetimeCountLess6hLevelMom  CounterBasedGauge64,
		psmModelLifetimeCountLess6hLevelMax  CounterBasedGauge64
	}

psmModelLifetimeCountLess6hLevelName OBJECT-TYPE
	SYNTAX      DisplayString
	MAX-ACCESS  not-accessible
	STATUS      current
	DESCRIPTION
	"Lifetime count <= 6h"
	::={ psmModelLifetimeCountLess6hLevelEntry 1}

psmModelLifetimeCountLess6hLevelVal OBJECT-TYPE
	SYNTAX     Counter64
	MAX-ACCESS read-only
	STATUS     current
	DESCRIPTION
	"Lifetime count <= 6h"
	::={ psmModelLifetimeCountLess6hLevelEntry 2 }

psmModelLifetimeCountLess6hLevelMom OBJECT-TYPE
	SYNTAX     CounterBasedGauge64
	MAX-ACCESS read-only
	STATUS     current
	DESCRIPTION
	"Lifetime count <= 6h"
	::={ psmModelLifetimeCountLess6hLevelEntry 3 }

psmModelLifetimeCountLess6hLevelMax OBJECT-TYPE
	SYNTAX     CounterBasedGauge64
	MAX-ACCESS read-only
	STATUS     current
	DESCRIPTION
	"Lifetime count <= 6h"
	::={ psmModelLifetimeCountLess6hLevelEntry 4 }

psmModelMaxObjectCount OBJECT IDENTIFIER ::= { psmModel 19 }

psmModelMaxObjectCountVal OBJECT-TYPE
	SYNTAX     Counter64
	MAX-ACCESS read-only
	STATUS     current
	DESCRIPTION "Max object count"

	::={ psmModelMaxObjectCount 1 }

psmModelMaxObjectCountMom OBJECT-TYPE
	SYNTAX     CounterBasedGauge64
	MAX-ACCESS read-only
	STATUS     current
	DESCRIPTION "Max object count"

	::={ psmModelMaxObjectCount 2 }

psmModelMaxObjectCountMax OBJECT-TYPE
	SYNTAX     CounterBasedGauge64
	MAX-ACCESS read-only
	STATUS     current
	DESCRIPTION "Max object count"

	::={ psmModelMaxObjectCount 3 }

psmModelMaxObjectCountLevelTable OBJECT-TYPE
	SYNTAX     SEQUENCE OF PsmModelMaxObjectCountLevelEntry
	MAX-ACCESS not-accessible
	STATUS     current
	DESCRIPTION
	"Max object count"
	::={ psmModelMaxObjectCount 4 }

psmModelMaxObjectCountLevelEntry OBJECT-TYPE
	SYNTAX      PsmModelMaxObjectCountLevelEntry
	MAX-ACCESS  not-accessible
	STATUS      current
	DESCRIPTION
	"Max object count"
	INDEX { psmModelMaxObjectCountLevelName }
	::={ psmModelMaxObjectCountLevelTable 1 }

PsmModelMaxObjectCountLevelEntry ::=
	SEQUENCE {
		psmModelMaxObjectCountLevelName DisplayString,
		psmModelMaxObjectCountLevelVal  Counter64,
		psmModelMaxObjectCountLevelMom  CounterBasedGauge64,
		psmModelMaxObjectCountLevelMax  CounterBasedGauge64
	}

psmModelMaxObjectCountLevelName OBJECT-TYPE
	SYNTAX      DisplayString
	MAX-ACCESS  not-accessible
	STATUS      current
	DESCRIPTION
	"Max object count"
	::={ psmModelMaxObjectCountLevelEntry 1}

psmModelMaxObjectCountLevelVal OBJECT-TYPE
	SYNTAX     Counter64
	MAX-ACCESS read-only
	STATUS     current
	DESCRIPTION
	"Max object count"
	::={ psmModelMaxObjectCountLevelEntry 2 }

psmModelMaxObjectCountLevelMom OBJECT-TYPE
	SYNTAX     CounterBasedGauge64
	MAX-ACCESS read-only
	STATUS     current
	DESCRIPTION
	"Max object count"
	::={ psmModelMaxObjectCountLevelEntry 3 }

psmModelMaxObjectCountLevelMax OBJECT-TYPE
	SYNTAX     CounterBasedGauge64
	MAX-ACCESS read-only
	STATUS     current
	DESCRIPTION
	"Max object count"
	::={ psmModelMaxObjectCountLevelEntry 4 }

psmModelModelFlushesdeprecated OBJECT IDENTIFIER ::= { psmModel 20 }

psmModelModelFlushesdeprecatedVal OBJECT-TYPE
	SYNTAX     Counter64
	MAX-ACCESS read-only
	STATUS     current
	DESCRIPTION "Model flushes (deprecated)"

	::={ psmModelModelFlushesdeprecated 1 }

psmModelModelFlushesdeprecatedMom OBJECT-TYPE
	SYNTAX     CounterBasedGauge64
	MAX-ACCESS read-only
	STATUS     current
	DESCRIPTION "Model flushes (deprecated)"

	::={ psmModelModelFlushesdeprecated 2 }

psmModelModelFlushesdeprecatedMax OBJECT-TYPE
	SYNTAX     CounterBasedGauge64
	MAX-ACCESS read-only
	STATUS     current
	DESCRIPTION "Model flushes (deprecated)"

	::={ psmModelModelFlushesdeprecated 3 }

psmModelModelFlushesdeprecatedLevelTable OBJECT-TYPE
	SYNTAX     SEQUENCE OF PsmModelModelFlushesdeprecatedLevelEntry
	MAX-ACCESS not-accessible
	STATUS     current
	DESCRIPTION
	"Model flushes (deprecated)"
	::={ psmModelModelFlushesdeprecated 4 }

psmModelModelFlushesdeprecatedLevelEntry OBJECT-TYPE
	SYNTAX      PsmModelModelFlushesdeprecatedLevelEntry
	MAX-ACCESS  not-accessible
	STATUS      current
	DESCRIPTION
	"Model flushes (deprecated)"
	INDEX { psmModelModelFlushesdeprecatedLevelName }
	::={ psmModelModelFlushesdeprecatedLevelTable 1 }

PsmModelModelFlushesdeprecatedLevelEntry ::=
	SEQUENCE {
		psmModelModelFlushesdeprecatedLevelName DisplayString,
		psmModelModelFlushesdeprecatedLevelVal  Counter64,
		psmModelModelFlushesdeprecatedLevelMom  CounterBasedGauge64,
		psmModelModelFlushesdeprecatedLevelMax  CounterBasedGauge64
	}

psmModelModelFlushesdeprecatedLevelName OBJECT-TYPE
	SYNTAX      DisplayString
	MAX-ACCESS  not-accessible
	STATUS      current
	DESCRIPTION
	"Model flushes (deprecated)"
	::={ psmModelModelFlushesdeprecatedLevelEntry 1}

psmModelModelFlushesdeprecatedLevelVal OBJECT-TYPE
	SYNTAX     Counter64
	MAX-ACCESS read-only
	STATUS     current
	DESCRIPTION
	"Model flushes (deprecated)"
	::={ psmModelModelFlushesdeprecatedLevelEntry 2 }

psmModelModelFlushesdeprecatedLevelMom OBJECT-TYPE
	SYNTAX     CounterBasedGauge64
	MAX-ACCESS read-only
	STATUS     current
	DESCRIPTION
	"Model flushes (deprecated)"
	::={ psmModelModelFlushesdeprecatedLevelEntry 3 }

psmModelModelFlushesdeprecatedLevelMax OBJECT-TYPE
	SYNTAX     CounterBasedGauge64
	MAX-ACCESS read-only
	STATUS     current
	DESCRIPTION
	"Model flushes (deprecated)"
	::={ psmModelModelFlushesdeprecatedLevelEntry 4 }

psmModelModelInputQueueCapacity OBJECT IDENTIFIER ::= { psmModel 21 }

psmModelModelInputQueueCapacityVal OBJECT-TYPE
	SYNTAX     Counter64
	MAX-ACCESS read-only
	STATUS     current
	DESCRIPTION "Model input queue capacity"

	::={ psmModelModelInputQueueCapacity 1 }

psmModelModelInputQueueCapacityMom OBJECT-TYPE
	SYNTAX     CounterBasedGauge64
	MAX-ACCESS read-only
	STATUS     current
	DESCRIPTION "Model input queue capacity"

	::={ psmModelModelInputQueueCapacity 2 }

psmModelModelInputQueueCapacityMax OBJECT-TYPE
	SYNTAX     CounterBasedGauge64
	MAX-ACCESS read-only
	STATUS     current
	DESCRIPTION "Model input queue capacity"

	::={ psmModelModelInputQueueCapacity 3 }

psmModelModelInputQueueCapacityLevelTable OBJECT-TYPE
	SYNTAX     SEQUENCE OF PsmModelModelInputQueueCapacityLevelEntry
	MAX-ACCESS not-accessible
	STATUS     current
	DESCRIPTION
	"Model input queue capacity"
	::={ psmModelModelInputQueueCapacity 4 }

psmModelModelInputQueueCapacityLevelEntry OBJECT-TYPE
	SYNTAX      PsmModelModelInputQueueCapacityLevelEntry
	MAX-ACCESS  not-accessible
	STATUS      current
	DESCRIPTION
	"Model input queue capacity"
	INDEX { psmModelModelInputQueueCapacityLevelName }
	::={ psmModelModelInputQueueCapacityLevelTable 1 }

PsmModelModelInputQueueCapacityLevelEntry ::=
	SEQUENCE {
		psmModelModelInputQueueCapacityLevelName DisplayString,
		psmModelModelInputQueueCapacityLevelVal  Counter64,
		psmModelModelInputQueueCapacityLevelMom  CounterBasedGauge64,
		psmModelModelInputQueueCapacityLevelMax  CounterBasedGauge64
	}

psmModelModelInputQueueCapacityLevelName OBJECT-TYPE
	SYNTAX      DisplayString
	MAX-ACCESS  not-accessible
	STATUS      current
	DESCRIPTION
	"Model input queue capacity"
	::={ psmModelModelInputQueueCapacityLevelEntry 1}

psmModelModelInputQueueCapacityLevelVal OBJECT-TYPE
	SYNTAX     Counter64
	MAX-ACCESS read-only
	STATUS     current
	DESCRIPTION
	"Model input queue capacity"
	::={ psmModelModelInputQueueCapacityLevelEntry 2 }

psmModelModelInputQueueCapacityLevelMom OBJECT-TYPE
	SYNTAX     CounterBasedGauge64
	MAX-ACCESS read-only
	STATUS     current
	DESCRIPTION
	"Model input queue capacity"
	::={ psmModelModelInputQueueCapacityLevelEntry 3 }

psmModelModelInputQueueCapacityLevelMax OBJECT-TYPE
	SYNTAX     CounterBasedGauge64
	MAX-ACCESS read-only
	STATUS     current
	DESCRIPTION
	"Model input queue capacity"
	::={ psmModelModelInputQueueCapacityLevelEntry 4 }

psmModelModelInputQueueSize OBJECT IDENTIFIER ::= { psmModel 22 }

psmModelModelInputQueueSizeVal OBJECT-TYPE
	SYNTAX     Counter64
	MAX-ACCESS read-only
	STATUS     current
	DESCRIPTION "Model input queue size"

	::={ psmModelModelInputQueueSize 1 }

psmModelModelInputQueueSizeMom OBJECT-TYPE
	SYNTAX     CounterBasedGauge64
	MAX-ACCESS read-only
	STATUS     current
	DESCRIPTION "Model input queue size"

	::={ psmModelModelInputQueueSize 2 }

psmModelModelInputQueueSizeMax OBJECT-TYPE
	SYNTAX     CounterBasedGauge64
	MAX-ACCESS read-only
	STATUS     current
	DESCRIPTION "Model input queue size"

	::={ psmModelModelInputQueueSize 3 }

psmModelModelInputQueueSizeLevelTable OBJECT-TYPE
	SYNTAX     SEQUENCE OF PsmModelModelInputQueueSizeLevelEntry
	MAX-ACCESS not-accessible
	STATUS     current
	DESCRIPTION
	"Model input queue size"
	::={ psmModelModelInputQueueSize 4 }

psmModelModelInputQueueSizeLevelEntry OBJECT-TYPE
	SYNTAX      PsmModelModelInputQueueSizeLevelEntry
	MAX-ACCESS  not-accessible
	STATUS      current
	DESCRIPTION
	"Model input queue size"
	INDEX { psmModelModelInputQueueSizeLevelName }
	::={ psmModelModelInputQueueSizeLevelTable 1 }

PsmModelModelInputQueueSizeLevelEntry ::=
	SEQUENCE {
		psmModelModelInputQueueSizeLevelName DisplayString,
		psmModelModelInputQueueSizeLevelVal  Counter64,
		psmModelModelInputQueueSizeLevelMom  CounterBasedGauge64,
		psmModelModelInputQueueSizeLevelMax  CounterBasedGauge64
	}

psmModelModelInputQueueSizeLevelName OBJECT-TYPE
	SYNTAX      DisplayString
	MAX-ACCESS  not-accessible
	STATUS      current
	DESCRIPTION
	"Model input queue size"
	::={ psmModelModelInputQueueSizeLevelEntry 1}

psmModelModelInputQueueSizeLevelVal OBJECT-TYPE
	SYNTAX     Counter64
	MAX-ACCESS read-only
	STATUS     current
	DESCRIPTION
	"Model input queue size"
	::={ psmModelModelInputQueueSizeLevelEntry 2 }

psmModelModelInputQueueSizeLevelMom OBJECT-TYPE
	SYNTAX     CounterBasedGauge64
	MAX-ACCESS read-only
	STATUS     current
	DESCRIPTION
	"Model input queue size"
	::={ psmModelModelInputQueueSizeLevelEntry 3 }

psmModelModelInputQueueSizeLevelMax OBJECT-TYPE
	SYNTAX     CounterBasedGauge64
	MAX-ACCESS read-only
	STATUS     current
	DESCRIPTION
	"Model input queue size"
	::={ psmModelModelInputQueueSizeLevelEntry 4 }

psmModelModelOutputQueueCapacity OBJECT IDENTIFIER ::= { psmModel 23 }

psmModelModelOutputQueueCapacityVal OBJECT-TYPE
	SYNTAX     Counter64
	MAX-ACCESS read-only
	STATUS     current
	DESCRIPTION "Model output queue capacity"

	::={ psmModelModelOutputQueueCapacity 1 }

psmModelModelOutputQueueCapacityMom OBJECT-TYPE
	SYNTAX     CounterBasedGauge64
	MAX-ACCESS read-only
	STATUS     current
	DESCRIPTION "Model output queue capacity"

	::={ psmModelModelOutputQueueCapacity 2 }

psmModelModelOutputQueueCapacityMax OBJECT-TYPE
	SYNTAX     CounterBasedGauge64
	MAX-ACCESS read-only
	STATUS     current
	DESCRIPTION "Model output queue capacity"

	::={ psmModelModelOutputQueueCapacity 3 }

psmModelModelOutputQueueCapacityLevelTable OBJECT-TYPE
	SYNTAX     SEQUENCE OF PsmModelModelOutputQueueCapacityLevelEntry
	MAX-ACCESS not-accessible
	STATUS     current
	DESCRIPTION
	"Model output queue capacity"
	::={ psmModelModelOutputQueueCapacity 4 }

psmModelModelOutputQueueCapacityLevelEntry OBJECT-TYPE
	SYNTAX      PsmModelModelOutputQueueCapacityLevelEntry
	MAX-ACCESS  not-accessible
	STATUS      current
	DESCRIPTION
	"Model output queue capacity"
	INDEX { psmModelModelOutputQueueCapacityLevelName }
	::={ psmModelModelOutputQueueCapacityLevelTable 1 }

PsmModelModelOutputQueueCapacityLevelEntry ::=
	SEQUENCE {
		psmModelModelOutputQueueCapacityLevelName DisplayString,
		psmModelModelOutputQueueCapacityLevelVal  Counter64,
		psmModelModelOutputQueueCapacityLevelMom  CounterBasedGauge64,
		psmModelModelOutputQueueCapacityLevelMax  CounterBasedGauge64
	}

psmModelModelOutputQueueCapacityLevelName OBJECT-TYPE
	SYNTAX      DisplayString
	MAX-ACCESS  not-accessible
	STATUS      current
	DESCRIPTION
	"Model output queue capacity"
	::={ psmModelModelOutputQueueCapacityLevelEntry 1}

psmModelModelOutputQueueCapacityLevelVal OBJECT-TYPE
	SYNTAX     Counter64
	MAX-ACCESS read-only
	STATUS     current
	DESCRIPTION
	"Model output queue capacity"
	::={ psmModelModelOutputQueueCapacityLevelEntry 2 }

psmModelModelOutputQueueCapacityLevelMom OBJECT-TYPE
	SYNTAX     CounterBasedGauge64
	MAX-ACCESS read-only
	STATUS     current
	DESCRIPTION
	"Model output queue capacity"
	::={ psmModelModelOutputQueueCapacityLevelEntry 3 }

psmModelModelOutputQueueCapacityLevelMax OBJECT-TYPE
	SYNTAX     CounterBasedGauge64
	MAX-ACCESS read-only
	STATUS     current
	DESCRIPTION
	"Model output queue capacity"
	::={ psmModelModelOutputQueueCapacityLevelEntry 4 }

psmModelModelOutputQueueSize OBJECT IDENTIFIER ::= { psmModel 24 }

psmModelModelOutputQueueSizeVal OBJECT-TYPE
	SYNTAX     Counter64
	MAX-ACCESS read-only
	STATUS     current
	DESCRIPTION "Model output queue size"

	::={ psmModelModelOutputQueueSize 1 }

psmModelModelOutputQueueSizeMom OBJECT-TYPE
	SYNTAX     CounterBasedGauge64
	MAX-ACCESS read-only
	STATUS     current
	DESCRIPTION "Model output queue size"

	::={ psmModelModelOutputQueueSize 2 }

psmModelModelOutputQueueSizeMax OBJECT-TYPE
	SYNTAX     CounterBasedGauge64
	MAX-ACCESS read-only
	STATUS     current
	DESCRIPTION "Model output queue size"

	::={ psmModelModelOutputQueueSize 3 }

psmModelModelOutputQueueSizeLevelTable OBJECT-TYPE
	SYNTAX     SEQUENCE OF PsmModelModelOutputQueueSizeLevelEntry
	MAX-ACCESS not-accessible
	STATUS     current
	DESCRIPTION
	"Model output queue size"
	::={ psmModelModelOutputQueueSize 4 }

psmModelModelOutputQueueSizeLevelEntry OBJECT-TYPE
	SYNTAX      PsmModelModelOutputQueueSizeLevelEntry
	MAX-ACCESS  not-accessible
	STATUS      current
	DESCRIPTION
	"Model output queue size"
	INDEX { psmModelModelOutputQueueSizeLevelName }
	::={ psmModelModelOutputQueueSizeLevelTable 1 }

PsmModelModelOutputQueueSizeLevelEntry ::=
	SEQUENCE {
		psmModelModelOutputQueueSizeLevelName DisplayString,
		psmModelModelOutputQueueSizeLevelVal  Counter64,
		psmModelModelOutputQueueSizeLevelMom  CounterBasedGauge64,
		psmModelModelOutputQueueSizeLevelMax  CounterBasedGauge64
	}

psmModelModelOutputQueueSizeLevelName OBJECT-TYPE
	SYNTAX      DisplayString
	MAX-ACCESS  not-accessible
	STATUS      current
	DESCRIPTION
	"Model output queue size"
	::={ psmModelModelOutputQueueSizeLevelEntry 1}

psmModelModelOutputQueueSizeLevelVal OBJECT-TYPE
	SYNTAX     Counter64
	MAX-ACCESS read-only
	STATUS     current
	DESCRIPTION
	"Model output queue size"
	::={ psmModelModelOutputQueueSizeLevelEntry 2 }

psmModelModelOutputQueueSizeLevelMom OBJECT-TYPE
	SYNTAX     CounterBasedGauge64
	MAX-ACCESS read-only
	STATUS     current
	DESCRIPTION
	"Model output queue size"
	::={ psmModelModelOutputQueueSizeLevelEntry 3 }

psmModelModelOutputQueueSizeLevelMax OBJECT-TYPE
	SYNTAX     CounterBasedGauge64
	MAX-ACCESS read-only
	STATUS     current
	DESCRIPTION
	"Model output queue size"
	::={ psmModelModelOutputQueueSizeLevelEntry 4 }

psmModelModelRequests OBJECT IDENTIFIER ::= { psmModel 25 }

psmModelModelRequestsVal OBJECT-TYPE
	SYNTAX     Counter64
	MAX-ACCESS read-only
	STATUS     current
	DESCRIPTION "Model requests"

	::={ psmModelModelRequests 1 }

psmModelModelRequestsMom OBJECT-TYPE
	SYNTAX     CounterBasedGauge64
	MAX-ACCESS read-only
	STATUS     current
	DESCRIPTION "Model requests"

	::={ psmModelModelRequests 2 }

psmModelModelRequestsMax OBJECT-TYPE
	SYNTAX     CounterBasedGauge64
	MAX-ACCESS read-only
	STATUS     current
	DESCRIPTION "Model requests"

	::={ psmModelModelRequests 3 }

psmModelModelRequestsLevelTable OBJECT-TYPE
	SYNTAX     SEQUENCE OF PsmModelModelRequestsLevelEntry
	MAX-ACCESS not-accessible
	STATUS     current
	DESCRIPTION
	"Model requests"
	::={ psmModelModelRequests 4 }

psmModelModelRequestsLevelEntry OBJECT-TYPE
	SYNTAX      PsmModelModelRequestsLevelEntry
	MAX-ACCESS  not-accessible
	STATUS      current
	DESCRIPTION
	"Model requests"
	INDEX { psmModelModelRequestsLevelName }
	::={ psmModelModelRequestsLevelTable 1 }

PsmModelModelRequestsLevelEntry ::=
	SEQUENCE {
		psmModelModelRequestsLevelName DisplayString,
		psmModelModelRequestsLevelVal  Counter64,
		psmModelModelRequestsLevelMom  CounterBasedGauge64,
		psmModelModelRequestsLevelMax  CounterBasedGauge64
	}

psmModelModelRequestsLevelName OBJECT-TYPE
	SYNTAX      DisplayString
	MAX-ACCESS  not-accessible
	STATUS      current
	DESCRIPTION
	"Model requests"
	::={ psmModelModelRequestsLevelEntry 1}

psmModelModelRequestsLevelVal OBJECT-TYPE
	SYNTAX     Counter64
	MAX-ACCESS read-only
	STATUS     current
	DESCRIPTION
	"Model requests"
	::={ psmModelModelRequestsLevelEntry 2 }

psmModelModelRequestsLevelMom OBJECT-TYPE
	SYNTAX     CounterBasedGauge64
	MAX-ACCESS read-only
	STATUS     current
	DESCRIPTION
	"Model requests"
	::={ psmModelModelRequestsLevelEntry 3 }

psmModelModelRequestsLevelMax OBJECT-TYPE
	SYNTAX     CounterBasedGauge64
	MAX-ACCESS read-only
	STATUS     current
	DESCRIPTION
	"Model requests"
	::={ psmModelModelRequestsLevelEntry 4 }

psmModelModelServiceState OBJECT IDENTIFIER ::= { psmModel 26 }

psmModelModelServiceStateVal OBJECT-TYPE
	SYNTAX     INTEGER {
		noModel(0),
		building(1),
		verifying(2),
		readonly(3),
		writable(4)
	}
	MAX-ACCESS read-only
	STATUS     current
	DESCRIPTION "Model service state"

	::={ psmModelModelServiceState 1 }

psmModelModelServiceStateLevelTable OBJECT-TYPE
	SYNTAX     SEQUENCE OF PsmModelModelServiceStateLevelEntry
	MAX-ACCESS not-accessible
	STATUS     current
	DESCRIPTION
	"Model service state"
	::={ psmModelModelServiceState 4 }

psmModelModelServiceStateLevelEntry OBJECT-TYPE
	SYNTAX      PsmModelModelServiceStateLevelEntry
	MAX-ACCESS  not-accessible
	STATUS      current
	DESCRIPTION
	"Model service state"
	INDEX { psmModelModelServiceStateLevelName }
	::={ psmModelModelServiceStateLevelTable 1 }

PsmModelModelServiceStateLevelEntry ::=
	SEQUENCE {
		psmModelModelServiceStateLevelName DisplayString,
		psmModelModelServiceStateLevelVal  INTEGER
	}

psmModelModelServiceStateLevelName OBJECT-TYPE
	SYNTAX      DisplayString
	MAX-ACCESS  not-accessible
	STATUS      current
	DESCRIPTION
	"Model service state"
	::={ psmModelModelServiceStateLevelEntry 1}

psmModelModelServiceStateLevelVal OBJECT-TYPE
	SYNTAX     INTEGER {
		noModel(0),
		building(1),
		verifying(2),
		readonly(3),
		writable(4)
	}
	MAX-ACCESS read-only
	STATUS     current
	DESCRIPTION
	"Model service state"
	::={ psmModelModelServiceStateLevelEntry 2 }

psmModelModelState OBJECT IDENTIFIER ::= { psmModel 27 }

psmModelModelStateVal OBJECT-TYPE
	SYNTAX     INTEGER {
		noModel(0),
		building(1),
		verifying(2),
		readonly(3),
		writable(4)
	}
	MAX-ACCESS read-only
	STATUS     current
	DESCRIPTION "Model state"

	::={ psmModelModelState 1 }

psmModelModelStateLevelTable OBJECT-TYPE
	SYNTAX     SEQUENCE OF PsmModelModelStateLevelEntry
	MAX-ACCESS not-accessible
	STATUS     current
	DESCRIPTION
	"Model state"
	::={ psmModelModelState 4 }

psmModelModelStateLevelEntry OBJECT-TYPE
	SYNTAX      PsmModelModelStateLevelEntry
	MAX-ACCESS  not-accessible
	STATUS      current
	DESCRIPTION
	"Model state"
	INDEX { psmModelModelStateLevelName }
	::={ psmModelModelStateLevelTable 1 }

PsmModelModelStateLevelEntry ::=
	SEQUENCE {
		psmModelModelStateLevelName DisplayString,
		psmModelModelStateLevelVal  INTEGER
	}

psmModelModelStateLevelName OBJECT-TYPE
	SYNTAX      DisplayString
	MAX-ACCESS  not-accessible
	STATUS      current
	DESCRIPTION
	"Model state"
	::={ psmModelModelStateLevelEntry 1}

psmModelModelStateLevelVal OBJECT-TYPE
	SYNTAX     INTEGER {
		noModel(0),
		building(1),
		verifying(2),
		readonly(3),
		writable(4)
	}
	MAX-ACCESS read-only
	STATUS     current
	DESCRIPTION
	"Model state"
	::={ psmModelModelStateLevelEntry 2 }

psmModelModelTransactionsdeprecated OBJECT IDENTIFIER ::= { psmModel 28 }

psmModelModelTransactionsdeprecatedVal OBJECT-TYPE
	SYNTAX     Counter64
	MAX-ACCESS read-only
	STATUS     current
	DESCRIPTION "Model transactions (deprecated)"

	::={ psmModelModelTransactionsdeprecated 1 }

psmModelModelTransactionsdeprecatedMom OBJECT-TYPE
	SYNTAX     CounterBasedGauge64
	MAX-ACCESS read-only
	STATUS     current
	DESCRIPTION "Model transactions (deprecated)"

	::={ psmModelModelTransactionsdeprecated 2 }

psmModelModelTransactionsdeprecatedMax OBJECT-TYPE
	SYNTAX     CounterBasedGauge64
	MAX-ACCESS read-only
	STATUS     current
	DESCRIPTION "Model transactions (deprecated)"

	::={ psmModelModelTransactionsdeprecated 3 }

psmModelModelTransactionsdeprecatedLevelTable OBJECT-TYPE
	SYNTAX     SEQUENCE OF PsmModelModelTransactionsdeprecatedLevelEntry
	MAX-ACCESS not-accessible
	STATUS     current
	DESCRIPTION
	"Model transactions (deprecated)"
	::={ psmModelModelTransactionsdeprecated 4 }

psmModelModelTransactionsdeprecatedLevelEntry OBJECT-TYPE
	SYNTAX      PsmModelModelTransactionsdeprecatedLevelEntry
	MAX-ACCESS  not-accessible
	STATUS      current
	DESCRIPTION
	"Model transactions (deprecated)"
	INDEX { psmModelModelTransactionsdeprecatedLevelName }
	::={ psmModelModelTransactionsdeprecatedLevelTable 1 }

PsmModelModelTransactionsdeprecatedLevelEntry ::=
	SEQUENCE {
		psmModelModelTransactionsdeprecatedLevelName DisplayString,
		psmModelModelTransactionsdeprecatedLevelVal  Counter64,
		psmModelModelTransactionsdeprecatedLevelMom  CounterBasedGauge64,
		psmModelModelTransactionsdeprecatedLevelMax  CounterBasedGauge64
	}

psmModelModelTransactionsdeprecatedLevelName OBJECT-TYPE
	SYNTAX      DisplayString
	MAX-ACCESS  not-accessible
	STATUS      current
	DESCRIPTION
	"Model transactions (deprecated)"
	::={ psmModelModelTransactionsdeprecatedLevelEntry 1}

psmModelModelTransactionsdeprecatedLevelVal OBJECT-TYPE
	SYNTAX     Counter64
	MAX-ACCESS read-only
	STATUS     current
	DESCRIPTION
	"Model transactions (deprecated)"
	::={ psmModelModelTransactionsdeprecatedLevelEntry 2 }

psmModelModelTransactionsdeprecatedLevelMom OBJECT-TYPE
	SYNTAX     CounterBasedGauge64
	MAX-ACCESS read-only
	STATUS     current
	DESCRIPTION
	"Model transactions (deprecated)"
	::={ psmModelModelTransactionsdeprecatedLevelEntry 3 }

psmModelModelTransactionsdeprecatedLevelMax OBJECT-TYPE
	SYNTAX     CounterBasedGauge64
	MAX-ACCESS read-only
	STATUS     current
	DESCRIPTION
	"Model transactions (deprecated)"
	::={ psmModelModelTransactionsdeprecatedLevelEntry 4 }

psmModelModelUpdates OBJECT IDENTIFIER ::= { psmModel 29 }

psmModelModelUpdatesVal OBJECT-TYPE
	SYNTAX     Counter64
	MAX-ACCESS read-only
	STATUS     current
	DESCRIPTION "Model updates"

	::={ psmModelModelUpdates 1 }

psmModelModelUpdatesMom OBJECT-TYPE
	SYNTAX     CounterBasedGauge64
	MAX-ACCESS read-only
	STATUS     current
	DESCRIPTION "Model updates"

	::={ psmModelModelUpdates 2 }

psmModelModelUpdatesMax OBJECT-TYPE
	SYNTAX     CounterBasedGauge64
	MAX-ACCESS read-only
	STATUS     current
	DESCRIPTION "Model updates"

	::={ psmModelModelUpdates 3 }

psmModelModelUpdatesLevelTable OBJECT-TYPE
	SYNTAX     SEQUENCE OF PsmModelModelUpdatesLevelEntry
	MAX-ACCESS not-accessible
	STATUS     current
	DESCRIPTION
	"Model updates"
	::={ psmModelModelUpdates 4 }

psmModelModelUpdatesLevelEntry OBJECT-TYPE
	SYNTAX      PsmModelModelUpdatesLevelEntry
	MAX-ACCESS  not-accessible
	STATUS      current
	DESCRIPTION
	"Model updates"
	INDEX { psmModelModelUpdatesLevelName }
	::={ psmModelModelUpdatesLevelTable 1 }

PsmModelModelUpdatesLevelEntry ::=
	SEQUENCE {
		psmModelModelUpdatesLevelName DisplayString,
		psmModelModelUpdatesLevelVal  Counter64,
		psmModelModelUpdatesLevelMom  CounterBasedGauge64,
		psmModelModelUpdatesLevelMax  CounterBasedGauge64
	}

psmModelModelUpdatesLevelName OBJECT-TYPE
	SYNTAX      DisplayString
	MAX-ACCESS  not-accessible
	STATUS      current
	DESCRIPTION
	"Model updates"
	::={ psmModelModelUpdatesLevelEntry 1}

psmModelModelUpdatesLevelVal OBJECT-TYPE
	SYNTAX     Counter64
	MAX-ACCESS read-only
	STATUS     current
	DESCRIPTION
	"Model updates"
	::={ psmModelModelUpdatesLevelEntry 2 }

psmModelModelUpdatesLevelMom OBJECT-TYPE
	SYNTAX     CounterBasedGauge64
	MAX-ACCESS read-only
	STATUS     current
	DESCRIPTION
	"Model updates"
	::={ psmModelModelUpdatesLevelEntry 3 }

psmModelModelUpdatesLevelMax OBJECT-TYPE
	SYNTAX     CounterBasedGauge64
	MAX-ACCESS read-only
	STATUS     current
	DESCRIPTION
	"Model updates"
	::={ psmModelModelUpdatesLevelEntry 4 }

psmEmitterUDP OBJECT IDENTIFIER ::= { psmv2 16 }

psmEmitterUDPDroppedQueries OBJECT IDENTIFIER ::= { psmEmitterUDP 1 }

psmEmitterUDPDroppedQueriesVal OBJECT-TYPE
	SYNTAX     Counter64
	MAX-ACCESS read-only
	STATUS     current
	DESCRIPTION "Dropped Queries"

	::={ psmEmitterUDPDroppedQueries 1 }

psmEmitterUDPDroppedQueriesMom OBJECT-TYPE
	SYNTAX     CounterBasedGauge64
	MAX-ACCESS read-only
	STATUS     current
	DESCRIPTION "Dropped Queries"

	::={ psmEmitterUDPDroppedQueries 2 }

psmEmitterUDPDroppedQueriesMax OBJECT-TYPE
	SYNTAX     CounterBasedGauge64
	MAX-ACCESS read-only
	STATUS     current
	DESCRIPTION "Dropped Queries"

	::={ psmEmitterUDPDroppedQueries 3 }

psmEmitterUDPDroppedQueriesLevelTable OBJECT-TYPE
	SYNTAX     SEQUENCE OF PsmEmitterUDPDroppedQueriesLevelEntry
	MAX-ACCESS not-accessible
	STATUS     current
	DESCRIPTION
	"Dropped Queries"
	::={ psmEmitterUDPDroppedQueries 4 }

psmEmitterUDPDroppedQueriesLevelEntry OBJECT-TYPE
	SYNTAX      PsmEmitterUDPDroppedQueriesLevelEntry
	MAX-ACCESS  not-accessible
	STATUS      current
	DESCRIPTION
	"Dropped Queries"
	INDEX { psmEmitterUDPDroppedQueriesLevelName }
	::={ psmEmitterUDPDroppedQueriesLevelTable 1 }

PsmEmitterUDPDroppedQueriesLevelEntry ::=
	SEQUENCE {
		psmEmitterUDPDroppedQueriesLevelName DisplayString,
		psmEmitterUDPDroppedQueriesLevelVal  Counter64,
		psmEmitterUDPDroppedQueriesLevelMom  CounterBasedGauge64,
		psmEmitterUDPDroppedQueriesLevelMax  CounterBasedGauge64
	}

psmEmitterUDPDroppedQueriesLevelName OBJECT-TYPE
	SYNTAX      DisplayString
	MAX-ACCESS  not-accessible
	STATUS      current
	DESCRIPTION
	"Dropped Queries"
	::={ psmEmitterUDPDroppedQueriesLevelEntry 1}

psmEmitterUDPDroppedQueriesLevelVal OBJECT-TYPE
	SYNTAX     Counter64
	MAX-ACCESS read-only
	STATUS     current
	DESCRIPTION
	"Dropped Queries"
	::={ psmEmitterUDPDroppedQueriesLevelEntry 2 }

psmEmitterUDPDroppedQueriesLevelMom OBJECT-TYPE
	SYNTAX     CounterBasedGauge64
	MAX-ACCESS read-only
	STATUS     current
	DESCRIPTION
	"Dropped Queries"
	::={ psmEmitterUDPDroppedQueriesLevelEntry 3 }

psmEmitterUDPDroppedQueriesLevelMax OBJECT-TYPE
	SYNTAX     CounterBasedGauge64
	MAX-ACCESS read-only
	STATUS     current
	DESCRIPTION
	"Dropped Queries"
	::={ psmEmitterUDPDroppedQueriesLevelEntry 4 }

psmEmitterUDPQueries OBJECT IDENTIFIER ::= { psmEmitterUDP 2 }

psmEmitterUDPQueriesVal OBJECT-TYPE
	SYNTAX     Counter64
	MAX-ACCESS read-only
	STATUS     current
	DESCRIPTION "Queries"

	::={ psmEmitterUDPQueries 1 }

psmEmitterUDPQueriesMom OBJECT-TYPE
	SYNTAX     CounterBasedGauge64
	MAX-ACCESS read-only
	STATUS     current
	DESCRIPTION "Queries"

	::={ psmEmitterUDPQueries 2 }

psmEmitterUDPQueriesMax OBJECT-TYPE
	SYNTAX     CounterBasedGauge64
	MAX-ACCESS read-only
	STATUS     current
	DESCRIPTION "Queries"

	::={ psmEmitterUDPQueries 3 }

psmEmitterUDPQueriesLevelTable OBJECT-TYPE
	SYNTAX     SEQUENCE OF PsmEmitterUDPQueriesLevelEntry
	MAX-ACCESS not-accessible
	STATUS     current
	DESCRIPTION
	"Queries"
	::={ psmEmitterUDPQueries 4 }

psmEmitterUDPQueriesLevelEntry OBJECT-TYPE
	SYNTAX      PsmEmitterUDPQueriesLevelEntry
	MAX-ACCESS  not-accessible
	STATUS      current
	DESCRIPTION
	"Queries"
	INDEX { psmEmitterUDPQueriesLevelName }
	::={ psmEmitterUDPQueriesLevelTable 1 }

PsmEmitterUDPQueriesLevelEntry ::=
	SEQUENCE {
		psmEmitterUDPQueriesLevelName DisplayString,
		psmEmitterUDPQueriesLevelVal  Counter64,
		psmEmitterUDPQueriesLevelMom  CounterBasedGauge64,
		psmEmitterUDPQueriesLevelMax  CounterBasedGauge64
	}

psmEmitterUDPQueriesLevelName OBJECT-TYPE
	SYNTAX      DisplayString
	MAX-ACCESS  not-accessible
	STATUS      current
	DESCRIPTION
	"Queries"
	::={ psmEmitterUDPQueriesLevelEntry 1}

psmEmitterUDPQueriesLevelVal OBJECT-TYPE
	SYNTAX     Counter64
	MAX-ACCESS read-only
	STATUS     current
	DESCRIPTION
	"Queries"
	::={ psmEmitterUDPQueriesLevelEntry 2 }

psmEmitterUDPQueriesLevelMom OBJECT-TYPE
	SYNTAX     CounterBasedGauge64
	MAX-ACCESS read-only
	STATUS     current
	DESCRIPTION
	"Queries"
	::={ psmEmitterUDPQueriesLevelEntry 3 }

psmEmitterUDPQueriesLevelMax OBJECT-TYPE
	SYNTAX     CounterBasedGauge64
	MAX-ACCESS read-only
	STATUS     current
	DESCRIPTION
	"Queries"
	::={ psmEmitterUDPQueriesLevelEntry 4 }

psmEmitterUDPReplies OBJECT IDENTIFIER ::= { psmEmitterUDP 3 }

psmEmitterUDPRepliesVal OBJECT-TYPE
	SYNTAX     Counter64
	MAX-ACCESS read-only
	STATUS     current
	DESCRIPTION "Replies"

	::={ psmEmitterUDPReplies 1 }

psmEmitterUDPRepliesMom OBJECT-TYPE
	SYNTAX     CounterBasedGauge64
	MAX-ACCESS read-only
	STATUS     current
	DESCRIPTION "Replies"

	::={ psmEmitterUDPReplies 2 }

psmEmitterUDPRepliesMax OBJECT-TYPE
	SYNTAX     CounterBasedGauge64
	MAX-ACCESS read-only
	STATUS     current
	DESCRIPTION "Replies"

	::={ psmEmitterUDPReplies 3 }

psmEmitterUDPRepliesLevelTable OBJECT-TYPE
	SYNTAX     SEQUENCE OF PsmEmitterUDPRepliesLevelEntry
	MAX-ACCESS not-accessible
	STATUS     current
	DESCRIPTION
	"Replies"
	::={ psmEmitterUDPReplies 4 }

psmEmitterUDPRepliesLevelEntry OBJECT-TYPE
	SYNTAX      PsmEmitterUDPRepliesLevelEntry
	MAX-ACCESS  not-accessible
	STATUS      current
	DESCRIPTION
	"Replies"
	INDEX { psmEmitterUDPRepliesLevelName }
	::={ psmEmitterUDPRepliesLevelTable 1 }

PsmEmitterUDPRepliesLevelEntry ::=
	SEQUENCE {
		psmEmitterUDPRepliesLevelName DisplayString,
		psmEmitterUDPRepliesLevelVal  Counter64,
		psmEmitterUDPRepliesLevelMom  CounterBasedGauge64,
		psmEmitterUDPRepliesLevelMax  CounterBasedGauge64
	}

psmEmitterUDPRepliesLevelName OBJECT-TYPE
	SYNTAX      DisplayString
	MAX-ACCESS  not-accessible
	STATUS      current
	DESCRIPTION
	"Replies"
	::={ psmEmitterUDPRepliesLevelEntry 1}

psmEmitterUDPRepliesLevelVal OBJECT-TYPE
	SYNTAX     Counter64
	MAX-ACCESS read-only
	STATUS     current
	DESCRIPTION
	"Replies"
	::={ psmEmitterUDPRepliesLevelEntry 2 }

psmEmitterUDPRepliesLevelMom OBJECT-TYPE
	SYNTAX     CounterBasedGauge64
	MAX-ACCESS read-only
	STATUS     current
	DESCRIPTION
	"Replies"
	::={ psmEmitterUDPRepliesLevelEntry 3 }

psmEmitterUDPRepliesLevelMax OBJECT-TYPE
	SYNTAX     CounterBasedGauge64
	MAX-ACCESS read-only
	STATUS     current
	DESCRIPTION
	"Replies"
	::={ psmEmitterUDPRepliesLevelEntry 4 }

psmEmitterUDPReplyFailures OBJECT IDENTIFIER ::= { psmEmitterUDP 4 }

psmEmitterUDPReplyFailuresVal OBJECT-TYPE
	SYNTAX     Counter64
	MAX-ACCESS read-only
	STATUS     current
	DESCRIPTION "Reply Failures"

	::={ psmEmitterUDPReplyFailures 1 }

psmEmitterUDPReplyFailuresMom OBJECT-TYPE
	SYNTAX     CounterBasedGauge64
	MAX-ACCESS read-only
	STATUS     current
	DESCRIPTION "Reply Failures"

	::={ psmEmitterUDPReplyFailures 2 }

psmEmitterUDPReplyFailuresMax OBJECT-TYPE
	SYNTAX     CounterBasedGauge64
	MAX-ACCESS read-only
	STATUS     current
	DESCRIPTION "Reply Failures"

	::={ psmEmitterUDPReplyFailures 3 }

psmEmitterUDPReplyFailuresLevelTable OBJECT-TYPE
	SYNTAX     SEQUENCE OF PsmEmitterUDPReplyFailuresLevelEntry
	MAX-ACCESS not-accessible
	STATUS     current
	DESCRIPTION
	"Reply Failures"
	::={ psmEmitterUDPReplyFailures 4 }

psmEmitterUDPReplyFailuresLevelEntry OBJECT-TYPE
	SYNTAX      PsmEmitterUDPReplyFailuresLevelEntry
	MAX-ACCESS  not-accessible
	STATUS      current
	DESCRIPTION
	"Reply Failures"
	INDEX { psmEmitterUDPReplyFailuresLevelName }
	::={ psmEmitterUDPReplyFailuresLevelTable 1 }

PsmEmitterUDPReplyFailuresLevelEntry ::=
	SEQUENCE {
		psmEmitterUDPReplyFailuresLevelName DisplayString,
		psmEmitterUDPReplyFailuresLevelVal  Counter64,
		psmEmitterUDPReplyFailuresLevelMom  CounterBasedGauge64,
		psmEmitterUDPReplyFailuresLevelMax  CounterBasedGauge64
	}

psmEmitterUDPReplyFailuresLevelName OBJECT-TYPE
	SYNTAX      DisplayString
	MAX-ACCESS  not-accessible
	STATUS      current
	DESCRIPTION
	"Reply Failures"
	::={ psmEmitterUDPReplyFailuresLevelEntry 1}

psmEmitterUDPReplyFailuresLevelVal OBJECT-TYPE
	SYNTAX     Counter64
	MAX-ACCESS read-only
	STATUS     current
	DESCRIPTION
	"Reply Failures"
	::={ psmEmitterUDPReplyFailuresLevelEntry 2 }

psmEmitterUDPReplyFailuresLevelMom OBJECT-TYPE
	SYNTAX     CounterBasedGauge64
	MAX-ACCESS read-only
	STATUS     current
	DESCRIPTION
	"Reply Failures"
	::={ psmEmitterUDPReplyFailuresLevelEntry 3 }

psmEmitterUDPReplyFailuresLevelMax OBJECT-TYPE
	SYNTAX     CounterBasedGauge64
	MAX-ACCESS read-only
	STATUS     current
	DESCRIPTION
	"Reply Failures"
	::={ psmEmitterUDPReplyFailuresLevelEntry 4 }

psmEmitterUDPReplyRejects OBJECT IDENTIFIER ::= { psmEmitterUDP 5 }

psmEmitterUDPReplyRejectsVal OBJECT-TYPE
	SYNTAX     Counter64
	MAX-ACCESS read-only
	STATUS     current
	DESCRIPTION "Reply Rejects"

	::={ psmEmitterUDPReplyRejects 1 }

psmEmitterUDPReplyRejectsMom OBJECT-TYPE
	SYNTAX     CounterBasedGauge64
	MAX-ACCESS read-only
	STATUS     current
	DESCRIPTION "Reply Rejects"

	::={ psmEmitterUDPReplyRejects 2 }

psmEmitterUDPReplyRejectsMax OBJECT-TYPE
	SYNTAX     CounterBasedGauge64
	MAX-ACCESS read-only
	STATUS     current
	DESCRIPTION "Reply Rejects"

	::={ psmEmitterUDPReplyRejects 3 }

psmEmitterUDPReplyRejectsLevelTable OBJECT-TYPE
	SYNTAX     SEQUENCE OF PsmEmitterUDPReplyRejectsLevelEntry
	MAX-ACCESS not-accessible
	STATUS     current
	DESCRIPTION
	"Reply Rejects"
	::={ psmEmitterUDPReplyRejects 4 }

psmEmitterUDPReplyRejectsLevelEntry OBJECT-TYPE
	SYNTAX      PsmEmitterUDPReplyRejectsLevelEntry
	MAX-ACCESS  not-accessible
	STATUS      current
	DESCRIPTION
	"Reply Rejects"
	INDEX { psmEmitterUDPReplyRejectsLevelName }
	::={ psmEmitterUDPReplyRejectsLevelTable 1 }

PsmEmitterUDPReplyRejectsLevelEntry ::=
	SEQUENCE {
		psmEmitterUDPReplyRejectsLevelName DisplayString,
		psmEmitterUDPReplyRejectsLevelVal  Counter64,
		psmEmitterUDPReplyRejectsLevelMom  CounterBasedGauge64,
		psmEmitterUDPReplyRejectsLevelMax  CounterBasedGauge64
	}

psmEmitterUDPReplyRejectsLevelName OBJECT-TYPE
	SYNTAX      DisplayString
	MAX-ACCESS  not-accessible
	STATUS      current
	DESCRIPTION
	"Reply Rejects"
	::={ psmEmitterUDPReplyRejectsLevelEntry 1}

psmEmitterUDPReplyRejectsLevelVal OBJECT-TYPE
	SYNTAX     Counter64
	MAX-ACCESS read-only
	STATUS     current
	DESCRIPTION
	"Reply Rejects"
	::={ psmEmitterUDPReplyRejectsLevelEntry 2 }

psmEmitterUDPReplyRejectsLevelMom OBJECT-TYPE
	SYNTAX     CounterBasedGauge64
	MAX-ACCESS read-only
	STATUS     current
	DESCRIPTION
	"Reply Rejects"
	::={ psmEmitterUDPReplyRejectsLevelEntry 3 }

psmEmitterUDPReplyRejectsLevelMax OBJECT-TYPE
	SYNTAX     CounterBasedGauge64
	MAX-ACCESS read-only
	STATUS     current
	DESCRIPTION
	"Reply Rejects"
	::={ psmEmitterUDPReplyRejectsLevelEntry 4 }

psmSourceIPDR OBJECT IDENTIFIER ::= { psmv2 14 }

psmSourceIPDRConnections OBJECT IDENTIFIER ::= { psmSourceIPDR 1 }

psmSourceIPDRConnectionsVal OBJECT-TYPE
	SYNTAX     Counter64
	MAX-ACCESS read-only
	STATUS     current
	DESCRIPTION "Connections"

	::={ psmSourceIPDRConnections 1 }

psmSourceIPDRConnectionsMom OBJECT-TYPE
	SYNTAX     CounterBasedGauge64
	MAX-ACCESS read-only
	STATUS     current
	DESCRIPTION "Connections"

	::={ psmSourceIPDRConnections 2 }

psmSourceIPDRConnectionsMax OBJECT-TYPE
	SYNTAX     CounterBasedGauge64
	MAX-ACCESS read-only
	STATUS     current
	DESCRIPTION "Connections"

	::={ psmSourceIPDRConnections 3 }

psmSourceIPDRConnectionsLevelTable OBJECT-TYPE
	SYNTAX     SEQUENCE OF PsmSourceIPDRConnectionsLevelEntry
	MAX-ACCESS not-accessible
	STATUS     current
	DESCRIPTION
	"Connections"
	::={ psmSourceIPDRConnections 4 }

psmSourceIPDRConnectionsLevelEntry OBJECT-TYPE
	SYNTAX      PsmSourceIPDRConnectionsLevelEntry
	MAX-ACCESS  not-accessible
	STATUS      current
	DESCRIPTION
	"Connections"
	INDEX { psmSourceIPDRConnectionsLevelName }
	::={ psmSourceIPDRConnectionsLevelTable 1 }

PsmSourceIPDRConnectionsLevelEntry ::=
	SEQUENCE {
		psmSourceIPDRConnectionsLevelName DisplayString,
		psmSourceIPDRConnectionsLevelVal  Counter64,
		psmSourceIPDRConnectionsLevelMom  CounterBasedGauge64,
		psmSourceIPDRConnectionsLevelMax  CounterBasedGauge64
	}

psmSourceIPDRConnectionsLevelName OBJECT-TYPE
	SYNTAX      DisplayString
	MAX-ACCESS  not-accessible
	STATUS      current
	DESCRIPTION
	"Connections"
	::={ psmSourceIPDRConnectionsLevelEntry 1}

psmSourceIPDRConnectionsLevelVal OBJECT-TYPE
	SYNTAX     Counter64
	MAX-ACCESS read-only
	STATUS     current
	DESCRIPTION
	"Connections"
	::={ psmSourceIPDRConnectionsLevelEntry 2 }

psmSourceIPDRConnectionsLevelMom OBJECT-TYPE
	SYNTAX     CounterBasedGauge64
	MAX-ACCESS read-only
	STATUS     current
	DESCRIPTION
	"Connections"
	::={ psmSourceIPDRConnectionsLevelEntry 3 }

psmSourceIPDRConnectionsLevelMax OBJECT-TYPE
	SYNTAX     CounterBasedGauge64
	MAX-ACCESS read-only
	STATUS     current
	DESCRIPTION
	"Connections"
	::={ psmSourceIPDRConnectionsLevelEntry 4 }

psmSourceIPDRFailures OBJECT IDENTIFIER ::= { psmSourceIPDR 2 }

psmSourceIPDRFailuresVal OBJECT-TYPE
	SYNTAX     Counter64
	MAX-ACCESS read-only
	STATUS     current
	DESCRIPTION "Failures"

	::={ psmSourceIPDRFailures 1 }

psmSourceIPDRFailuresMom OBJECT-TYPE
	SYNTAX     CounterBasedGauge64
	MAX-ACCESS read-only
	STATUS     current
	DESCRIPTION "Failures"

	::={ psmSourceIPDRFailures 2 }

psmSourceIPDRFailuresMax OBJECT-TYPE
	SYNTAX     CounterBasedGauge64
	MAX-ACCESS read-only
	STATUS     current
	DESCRIPTION "Failures"

	::={ psmSourceIPDRFailures 3 }

psmSourceIPDRFailuresLevelTable OBJECT-TYPE
	SYNTAX     SEQUENCE OF PsmSourceIPDRFailuresLevelEntry
	MAX-ACCESS not-accessible
	STATUS     current
	DESCRIPTION
	"Failures"
	::={ psmSourceIPDRFailures 4 }

psmSourceIPDRFailuresLevelEntry OBJECT-TYPE
	SYNTAX      PsmSourceIPDRFailuresLevelEntry
	MAX-ACCESS  not-accessible
	STATUS      current
	DESCRIPTION
	"Failures"
	INDEX { psmSourceIPDRFailuresLevelName }
	::={ psmSourceIPDRFailuresLevelTable 1 }

PsmSourceIPDRFailuresLevelEntry ::=
	SEQUENCE {
		psmSourceIPDRFailuresLevelName DisplayString,
		psmSourceIPDRFailuresLevelVal  Counter64,
		psmSourceIPDRFailuresLevelMom  CounterBasedGauge64,
		psmSourceIPDRFailuresLevelMax  CounterBasedGauge64
	}

psmSourceIPDRFailuresLevelName OBJECT-TYPE
	SYNTAX      DisplayString
	MAX-ACCESS  not-accessible
	STATUS      current
	DESCRIPTION
	"Failures"
	::={ psmSourceIPDRFailuresLevelEntry 1}

psmSourceIPDRFailuresLevelVal OBJECT-TYPE
	SYNTAX     Counter64
	MAX-ACCESS read-only
	STATUS     current
	DESCRIPTION
	"Failures"
	::={ psmSourceIPDRFailuresLevelEntry 2 }

psmSourceIPDRFailuresLevelMom OBJECT-TYPE
	SYNTAX     CounterBasedGauge64
	MAX-ACCESS read-only
	STATUS     current
	DESCRIPTION
	"Failures"
	::={ psmSourceIPDRFailuresLevelEntry 3 }

psmSourceIPDRFailuresLevelMax OBJECT-TYPE
	SYNTAX     CounterBasedGauge64
	MAX-ACCESS read-only
	STATUS     current
	DESCRIPTION
	"Failures"
	::={ psmSourceIPDRFailuresLevelEntry 4 }

psmSourceIPDRRequests OBJECT IDENTIFIER ::= { psmSourceIPDR 3 }

psmSourceIPDRRequestsVal OBJECT-TYPE
	SYNTAX     Counter64
	MAX-ACCESS read-only
	STATUS     current
	DESCRIPTION "Requests"

	::={ psmSourceIPDRRequests 1 }

psmSourceIPDRRequestsMom OBJECT-TYPE
	SYNTAX     CounterBasedGauge64
	MAX-ACCESS read-only
	STATUS     current
	DESCRIPTION "Requests"

	::={ psmSourceIPDRRequests 2 }

psmSourceIPDRRequestsMax OBJECT-TYPE
	SYNTAX     CounterBasedGauge64
	MAX-ACCESS read-only
	STATUS     current
	DESCRIPTION "Requests"

	::={ psmSourceIPDRRequests 3 }

psmSourceIPDRRequestsLevelTable OBJECT-TYPE
	SYNTAX     SEQUENCE OF PsmSourceIPDRRequestsLevelEntry
	MAX-ACCESS not-accessible
	STATUS     current
	DESCRIPTION
	"Requests"
	::={ psmSourceIPDRRequests 4 }

psmSourceIPDRRequestsLevelEntry OBJECT-TYPE
	SYNTAX      PsmSourceIPDRRequestsLevelEntry
	MAX-ACCESS  not-accessible
	STATUS      current
	DESCRIPTION
	"Requests"
	INDEX { psmSourceIPDRRequestsLevelName }
	::={ psmSourceIPDRRequestsLevelTable 1 }

PsmSourceIPDRRequestsLevelEntry ::=
	SEQUENCE {
		psmSourceIPDRRequestsLevelName DisplayString,
		psmSourceIPDRRequestsLevelVal  Counter64,
		psmSourceIPDRRequestsLevelMom  CounterBasedGauge64,
		psmSourceIPDRRequestsLevelMax  CounterBasedGauge64
	}

psmSourceIPDRRequestsLevelName OBJECT-TYPE
	SYNTAX      DisplayString
	MAX-ACCESS  not-accessible
	STATUS      current
	DESCRIPTION
	"Requests"
	::={ psmSourceIPDRRequestsLevelEntry 1}

psmSourceIPDRRequestsLevelVal OBJECT-TYPE
	SYNTAX     Counter64
	MAX-ACCESS read-only
	STATUS     current
	DESCRIPTION
	"Requests"
	::={ psmSourceIPDRRequestsLevelEntry 2 }

psmSourceIPDRRequestsLevelMom OBJECT-TYPE
	SYNTAX     CounterBasedGauge64
	MAX-ACCESS read-only
	STATUS     current
	DESCRIPTION
	"Requests"
	::={ psmSourceIPDRRequestsLevelEntry 3 }

psmSourceIPDRRequestsLevelMax OBJECT-TYPE
	SYNTAX     CounterBasedGauge64
	MAX-ACCESS read-only
	STATUS     current
	DESCRIPTION
	"Requests"
	::={ psmSourceIPDRRequestsLevelEntry 4 }

psmSourceIPDRTotalConnections OBJECT IDENTIFIER ::= { psmSourceIPDR 4 }

psmSourceIPDRTotalConnectionsVal OBJECT-TYPE
	SYNTAX     CounterBasedGauge64
	MAX-ACCESS read-only
	STATUS     current
	DESCRIPTION "Total connections"

	::={ psmSourceIPDRTotalConnections 1 }

psmSourceIPDRTotalConnectionsMax OBJECT-TYPE
	SYNTAX     CounterBasedGauge64
	MAX-ACCESS read-only
	STATUS     current
	DESCRIPTION "Total connections"

	::={ psmSourceIPDRTotalConnections 3 }

psmSourceIPDRTotalConnectionsLevelTable OBJECT-TYPE
	SYNTAX     SEQUENCE OF PsmSourceIPDRTotalConnectionsLevelEntry
	MAX-ACCESS not-accessible
	STATUS     current
	DESCRIPTION
	"Total connections"
	::={ psmSourceIPDRTotalConnections 4 }

psmSourceIPDRTotalConnectionsLevelEntry OBJECT-TYPE
	SYNTAX      PsmSourceIPDRTotalConnectionsLevelEntry
	MAX-ACCESS  not-accessible
	STATUS      current
	DESCRIPTION
	"Total connections"
	INDEX { psmSourceIPDRTotalConnectionsLevelName }
	::={ psmSourceIPDRTotalConnectionsLevelTable 1 }

PsmSourceIPDRTotalConnectionsLevelEntry ::=
	SEQUENCE {
		psmSourceIPDRTotalConnectionsLevelName DisplayString,
		psmSourceIPDRTotalConnectionsLevelVal  CounterBasedGauge64,
		psmSourceIPDRTotalConnectionsLevelMax  CounterBasedGauge64
	}

psmSourceIPDRTotalConnectionsLevelName OBJECT-TYPE
	SYNTAX      DisplayString
	MAX-ACCESS  not-accessible
	STATUS      current
	DESCRIPTION
	"Total connections"
	::={ psmSourceIPDRTotalConnectionsLevelEntry 1}

psmSourceIPDRTotalConnectionsLevelVal OBJECT-TYPE
	SYNTAX     CounterBasedGauge64
	MAX-ACCESS read-only
	STATUS     current
	DESCRIPTION
	"Total connections"
	::={ psmSourceIPDRTotalConnectionsLevelEntry 2 }

psmSourceIPDRTotalConnectionsLevelMax OBJECT-TYPE
	SYNTAX     CounterBasedGauge64
	MAX-ACCESS read-only
	STATUS     current
	DESCRIPTION
	"Total connections"
	::={ psmSourceIPDRTotalConnectionsLevelEntry 4 }

psmSourceREST OBJECT IDENTIFIER ::= { psmv2 12 }

psmSourceRESTFailures OBJECT IDENTIFIER ::= { psmSourceREST 1 }

psmSourceRESTFailuresVal OBJECT-TYPE
	SYNTAX     Counter64
	MAX-ACCESS read-only
	STATUS     current
	DESCRIPTION "Failures"

	::={ psmSourceRESTFailures 1 }

psmSourceRESTFailuresMom OBJECT-TYPE
	SYNTAX     CounterBasedGauge64
	MAX-ACCESS read-only
	STATUS     current
	DESCRIPTION "Failures"

	::={ psmSourceRESTFailures 2 }

psmSourceRESTFailuresMax OBJECT-TYPE
	SYNTAX     CounterBasedGauge64
	MAX-ACCESS read-only
	STATUS     current
	DESCRIPTION "Failures"

	::={ psmSourceRESTFailures 3 }

psmSourceRESTFailuresLevelTable OBJECT-TYPE
	SYNTAX     SEQUENCE OF PsmSourceRESTFailuresLevelEntry
	MAX-ACCESS not-accessible
	STATUS     current
	DESCRIPTION
	"Failures"
	::={ psmSourceRESTFailures 4 }

psmSourceRESTFailuresLevelEntry OBJECT-TYPE
	SYNTAX      PsmSourceRESTFailuresLevelEntry
	MAX-ACCESS  not-accessible
	STATUS      current
	DESCRIPTION
	"Failures"
	INDEX { psmSourceRESTFailuresLevelName }
	::={ psmSourceRESTFailuresLevelTable 1 }

PsmSourceRESTFailuresLevelEntry ::=
	SEQUENCE {
		psmSourceRESTFailuresLevelName DisplayString,
		psmSourceRESTFailuresLevelVal  Counter64,
		psmSourceRESTFailuresLevelMom  CounterBasedGauge64,
		psmSourceRESTFailuresLevelMax  CounterBasedGauge64
	}

psmSourceRESTFailuresLevelName OBJECT-TYPE
	SYNTAX      DisplayString
	MAX-ACCESS  not-accessible
	STATUS      current
	DESCRIPTION
	"Failures"
	::={ psmSourceRESTFailuresLevelEntry 1}

psmSourceRESTFailuresLevelVal OBJECT-TYPE
	SYNTAX     Counter64
	MAX-ACCESS read-only
	STATUS     current
	DESCRIPTION
	"Failures"
	::={ psmSourceRESTFailuresLevelEntry 2 }

psmSourceRESTFailuresLevelMom OBJECT-TYPE
	SYNTAX     CounterBasedGauge64
	MAX-ACCESS read-only
	STATUS     current
	DESCRIPTION
	"Failures"
	::={ psmSourceRESTFailuresLevelEntry 3 }

psmSourceRESTFailuresLevelMax OBJECT-TYPE
	SYNTAX     CounterBasedGauge64
	MAX-ACCESS read-only
	STATUS     current
	DESCRIPTION
	"Failures"
	::={ psmSourceRESTFailuresLevelEntry 4 }

psmSourceRESTRequests OBJECT IDENTIFIER ::= { psmSourceREST 2 }

psmSourceRESTRequestsVal OBJECT-TYPE
	SYNTAX     Counter64
	MAX-ACCESS read-only
	STATUS     current
	DESCRIPTION "Requests"

	::={ psmSourceRESTRequests 1 }

psmSourceRESTRequestsMom OBJECT-TYPE
	SYNTAX     CounterBasedGauge64
	MAX-ACCESS read-only
	STATUS     current
	DESCRIPTION "Requests"

	::={ psmSourceRESTRequests 2 }

psmSourceRESTRequestsMax OBJECT-TYPE
	SYNTAX     CounterBasedGauge64
	MAX-ACCESS read-only
	STATUS     current
	DESCRIPTION "Requests"

	::={ psmSourceRESTRequests 3 }

psmSourceRESTRequestsLevelTable OBJECT-TYPE
	SYNTAX     SEQUENCE OF PsmSourceRESTRequestsLevelEntry
	MAX-ACCESS not-accessible
	STATUS     current
	DESCRIPTION
	"Requests"
	::={ psmSourceRESTRequests 4 }

psmSourceRESTRequestsLevelEntry OBJECT-TYPE
	SYNTAX      PsmSourceRESTRequestsLevelEntry
	MAX-ACCESS  not-accessible
	STATUS      current
	DESCRIPTION
	"Requests"
	INDEX { psmSourceRESTRequestsLevelName }
	::={ psmSourceRESTRequestsLevelTable 1 }

PsmSourceRESTRequestsLevelEntry ::=
	SEQUENCE {
		psmSourceRESTRequestsLevelName DisplayString,
		psmSourceRESTRequestsLevelVal  Counter64,
		psmSourceRESTRequestsLevelMom  CounterBasedGauge64,
		psmSourceRESTRequestsLevelMax  CounterBasedGauge64
	}

psmSourceRESTRequestsLevelName OBJECT-TYPE
	SYNTAX      DisplayString
	MAX-ACCESS  not-accessible
	STATUS      current
	DESCRIPTION
	"Requests"
	::={ psmSourceRESTRequestsLevelEntry 1}

psmSourceRESTRequestsLevelVal OBJECT-TYPE
	SYNTAX     Counter64
	MAX-ACCESS read-only
	STATUS     current
	DESCRIPTION
	"Requests"
	::={ psmSourceRESTRequestsLevelEntry 2 }

psmSourceRESTRequestsLevelMom OBJECT-TYPE
	SYNTAX     CounterBasedGauge64
	MAX-ACCESS read-only
	STATUS     current
	DESCRIPTION
	"Requests"
	::={ psmSourceRESTRequestsLevelEntry 3 }

psmSourceRESTRequestsLevelMax OBJECT-TYPE
	SYNTAX     CounterBasedGauge64
	MAX-ACCESS read-only
	STATUS     current
	DESCRIPTION
	"Requests"
	::={ psmSourceRESTRequestsLevelEntry 4 }

psmProvisioner OBJECT IDENTIFIER ::= { psmv2 15 }

psmProvisionerAccountingState OBJECT IDENTIFIER ::= { psmProvisioner 1 }

psmProvisionerAccountingStateVal OBJECT-TYPE
	SYNTAX     INTEGER {
		updatesDropped(0),
		resendRequested(1),
		normal(2)
	}
	MAX-ACCESS read-only
	STATUS     current
	DESCRIPTION "Accounting state"

	::={ psmProvisionerAccountingState 1 }

psmProvisionerAccountingStateLevelTable OBJECT-TYPE
	SYNTAX     SEQUENCE OF PsmProvisionerAccountingStateLevelEntry
	MAX-ACCESS not-accessible
	STATUS     current
	DESCRIPTION
	"Accounting state"
	::={ psmProvisionerAccountingState 4 }

psmProvisionerAccountingStateLevelEntry OBJECT-TYPE
	SYNTAX      PsmProvisionerAccountingStateLevelEntry
	MAX-ACCESS  not-accessible
	STATUS      current
	DESCRIPTION
	"Accounting state"
	INDEX { psmProvisionerAccountingStateLevelName }
	::={ psmProvisionerAccountingStateLevelTable 1 }

PsmProvisionerAccountingStateLevelEntry ::=
	SEQUENCE {
		psmProvisionerAccountingStateLevelName DisplayString,
		psmProvisionerAccountingStateLevelVal  INTEGER
	}

psmProvisionerAccountingStateLevelName OBJECT-TYPE
	SYNTAX      DisplayString
	MAX-ACCESS  not-accessible
	STATUS      current
	DESCRIPTION
	"Accounting state"
	::={ psmProvisionerAccountingStateLevelEntry 1}

psmProvisionerAccountingStateLevelVal OBJECT-TYPE
	SYNTAX     INTEGER {
		updatesDropped(0),
		resendRequested(1),
		normal(2)
	}
	MAX-ACCESS read-only
	STATUS     current
	DESCRIPTION
	"Accounting state"
	::={ psmProvisionerAccountingStateLevelEntry 2 }

psmProvisionerBytesReceived OBJECT IDENTIFIER ::= { psmProvisioner 2 }

psmProvisionerBytesReceivedVal OBJECT-TYPE
	SYNTAX     Counter64
	MAX-ACCESS read-only
	STATUS     current
	DESCRIPTION "Bytes received"

	::={ psmProvisionerBytesReceived 1 }

psmProvisionerBytesReceivedMom OBJECT-TYPE
	SYNTAX     CounterBasedGauge64
	MAX-ACCESS read-only
	STATUS     current
	DESCRIPTION "Bytes received"

	::={ psmProvisionerBytesReceived 2 }

psmProvisionerBytesReceivedMax OBJECT-TYPE
	SYNTAX     CounterBasedGauge64
	MAX-ACCESS read-only
	STATUS     current
	DESCRIPTION "Bytes received"

	::={ psmProvisionerBytesReceived 3 }

psmProvisionerBytesReceivedLevelTable OBJECT-TYPE
	SYNTAX     SEQUENCE OF PsmProvisionerBytesReceivedLevelEntry
	MAX-ACCESS not-accessible
	STATUS     current
	DESCRIPTION
	"Bytes received"
	::={ psmProvisionerBytesReceived 4 }

psmProvisionerBytesReceivedLevelEntry OBJECT-TYPE
	SYNTAX      PsmProvisionerBytesReceivedLevelEntry
	MAX-ACCESS  not-accessible
	STATUS      current
	DESCRIPTION
	"Bytes received"
	INDEX { psmProvisionerBytesReceivedLevelName }
	::={ psmProvisionerBytesReceivedLevelTable 1 }

PsmProvisionerBytesReceivedLevelEntry ::=
	SEQUENCE {
		psmProvisionerBytesReceivedLevelName DisplayString,
		psmProvisionerBytesReceivedLevelVal  Counter64,
		psmProvisionerBytesReceivedLevelMom  CounterBasedGauge64,
		psmProvisionerBytesReceivedLevelMax  CounterBasedGauge64
	}

psmProvisionerBytesReceivedLevelName OBJECT-TYPE
	SYNTAX      DisplayString
	MAX-ACCESS  not-accessible
	STATUS      current
	DESCRIPTION
	"Bytes received"
	::={ psmProvisionerBytesReceivedLevelEntry 1}

psmProvisionerBytesReceivedLevelVal OBJECT-TYPE
	SYNTAX     Counter64
	MAX-ACCESS read-only
	STATUS     current
	DESCRIPTION
	"Bytes received"
	::={ psmProvisionerBytesReceivedLevelEntry 2 }

psmProvisionerBytesReceivedLevelMom OBJECT-TYPE
	SYNTAX     CounterBasedGauge64
	MAX-ACCESS read-only
	STATUS     current
	DESCRIPTION
	"Bytes received"
	::={ psmProvisionerBytesReceivedLevelEntry 3 }

psmProvisionerBytesReceivedLevelMax OBJECT-TYPE
	SYNTAX     CounterBasedGauge64
	MAX-ACCESS read-only
	STATUS     current
	DESCRIPTION
	"Bytes received"
	::={ psmProvisionerBytesReceivedLevelEntry 4 }

psmProvisionerBytesSent OBJECT IDENTIFIER ::= { psmProvisioner 3 }

psmProvisionerBytesSentVal OBJECT-TYPE
	SYNTAX     Counter64
	MAX-ACCESS read-only
	STATUS     current
	DESCRIPTION "Bytes sent"

	::={ psmProvisionerBytesSent 1 }

psmProvisionerBytesSentMom OBJECT-TYPE
	SYNTAX     CounterBasedGauge64
	MAX-ACCESS read-only
	STATUS     current
	DESCRIPTION "Bytes sent"

	::={ psmProvisionerBytesSent 2 }

psmProvisionerBytesSentMax OBJECT-TYPE
	SYNTAX     CounterBasedGauge64
	MAX-ACCESS read-only
	STATUS     current
	DESCRIPTION "Bytes sent"

	::={ psmProvisionerBytesSent 3 }

psmProvisionerBytesSentLevelTable OBJECT-TYPE
	SYNTAX     SEQUENCE OF PsmProvisionerBytesSentLevelEntry
	MAX-ACCESS not-accessible
	STATUS     current
	DESCRIPTION
	"Bytes sent"
	::={ psmProvisionerBytesSent 4 }

psmProvisionerBytesSentLevelEntry OBJECT-TYPE
	SYNTAX      PsmProvisionerBytesSentLevelEntry
	MAX-ACCESS  not-accessible
	STATUS      current
	DESCRIPTION
	"Bytes sent"
	INDEX { psmProvisionerBytesSentLevelName }
	::={ psmProvisionerBytesSentLevelTable 1 }

PsmProvisionerBytesSentLevelEntry ::=
	SEQUENCE {
		psmProvisionerBytesSentLevelName DisplayString,
		psmProvisionerBytesSentLevelVal  Counter64,
		psmProvisionerBytesSentLevelMom  CounterBasedGauge64,
		psmProvisionerBytesSentLevelMax  CounterBasedGauge64
	}

psmProvisionerBytesSentLevelName OBJECT-TYPE
	SYNTAX      DisplayString
	MAX-ACCESS  not-accessible
	STATUS      current
	DESCRIPTION
	"Bytes sent"
	::={ psmProvisionerBytesSentLevelEntry 1}

psmProvisionerBytesSentLevelVal OBJECT-TYPE
	SYNTAX     Counter64
	MAX-ACCESS read-only
	STATUS     current
	DESCRIPTION
	"Bytes sent"
	::={ psmProvisionerBytesSentLevelEntry 2 }

psmProvisionerBytesSentLevelMom OBJECT-TYPE
	SYNTAX     CounterBasedGauge64
	MAX-ACCESS read-only
	STATUS     current
	DESCRIPTION
	"Bytes sent"
	::={ psmProvisionerBytesSentLevelEntry 3 }

psmProvisionerBytesSentLevelMax OBJECT-TYPE
	SYNTAX     CounterBasedGauge64
	MAX-ACCESS read-only
	STATUS     current
	DESCRIPTION
	"Bytes sent"
	::={ psmProvisionerBytesSentLevelEntry 4 }

psmProvisionerErrors OBJECT IDENTIFIER ::= { psmProvisioner 4 }

psmProvisionerErrorsVal OBJECT-TYPE
	SYNTAX     Counter64
	MAX-ACCESS read-only
	STATUS     current
	DESCRIPTION "Errors"

	::={ psmProvisionerErrors 1 }

psmProvisionerErrorsMom OBJECT-TYPE
	SYNTAX     CounterBasedGauge64
	MAX-ACCESS read-only
	STATUS     current
	DESCRIPTION "Errors"

	::={ psmProvisionerErrors 2 }

psmProvisionerErrorsMax OBJECT-TYPE
	SYNTAX     CounterBasedGauge64
	MAX-ACCESS read-only
	STATUS     current
	DESCRIPTION "Errors"

	::={ psmProvisionerErrors 3 }

psmProvisionerErrorsLevelTable OBJECT-TYPE
	SYNTAX     SEQUENCE OF PsmProvisionerErrorsLevelEntry
	MAX-ACCESS not-accessible
	STATUS     current
	DESCRIPTION
	"Errors"
	::={ psmProvisionerErrors 4 }

psmProvisionerErrorsLevelEntry OBJECT-TYPE
	SYNTAX      PsmProvisionerErrorsLevelEntry
	MAX-ACCESS  not-accessible
	STATUS      current
	DESCRIPTION
	"Errors"
	INDEX { psmProvisionerErrorsLevelName }
	::={ psmProvisionerErrorsLevelTable 1 }

PsmProvisionerErrorsLevelEntry ::=
	SEQUENCE {
		psmProvisionerErrorsLevelName DisplayString,
		psmProvisionerErrorsLevelVal  Counter64,
		psmProvisionerErrorsLevelMom  CounterBasedGauge64,
		psmProvisionerErrorsLevelMax  CounterBasedGauge64
	}

psmProvisionerErrorsLevelName OBJECT-TYPE
	SYNTAX      DisplayString
	MAX-ACCESS  not-accessible
	STATUS      current
	DESCRIPTION
	"Errors"
	::={ psmProvisionerErrorsLevelEntry 1}

psmProvisionerErrorsLevelVal OBJECT-TYPE
	SYNTAX     Counter64
	MAX-ACCESS read-only
	STATUS     current
	DESCRIPTION
	"Errors"
	::={ psmProvisionerErrorsLevelEntry 2 }

psmProvisionerErrorsLevelMom OBJECT-TYPE
	SYNTAX     CounterBasedGauge64
	MAX-ACCESS read-only
	STATUS     current
	DESCRIPTION
	"Errors"
	::={ psmProvisionerErrorsLevelEntry 3 }

psmProvisionerErrorsLevelMax OBJECT-TYPE
	SYNTAX     CounterBasedGauge64
	MAX-ACCESS read-only
	STATUS     current
	DESCRIPTION
	"Errors"
	::={ psmProvisionerErrorsLevelEntry 4 }

psmProvisionerFailedCounterUpdates OBJECT IDENTIFIER ::= { psmProvisioner 5 }

psmProvisionerFailedCounterUpdatesVal OBJECT-TYPE
	SYNTAX     Counter64
	MAX-ACCESS read-only
	STATUS     current
	DESCRIPTION "Failed counter updates"

	::={ psmProvisionerFailedCounterUpdates 1 }

psmProvisionerFailedCounterUpdatesMom OBJECT-TYPE
	SYNTAX     CounterBasedGauge64
	MAX-ACCESS read-only
	STATUS     current
	DESCRIPTION "Failed counter updates"

	::={ psmProvisionerFailedCounterUpdates 2 }

psmProvisionerFailedCounterUpdatesMax OBJECT-TYPE
	SYNTAX     CounterBasedGauge64
	MAX-ACCESS read-only
	STATUS     current
	DESCRIPTION "Failed counter updates"

	::={ psmProvisionerFailedCounterUpdates 3 }

psmProvisionerFailedCounterUpdatesLevelTable OBJECT-TYPE
	SYNTAX     SEQUENCE OF PsmProvisionerFailedCounterUpdatesLevelEntry
	MAX-ACCESS not-accessible
	STATUS     current
	DESCRIPTION
	"Failed counter updates"
	::={ psmProvisionerFailedCounterUpdates 4 }

psmProvisionerFailedCounterUpdatesLevelEntry OBJECT-TYPE
	SYNTAX      PsmProvisionerFailedCounterUpdatesLevelEntry
	MAX-ACCESS  not-accessible
	STATUS      current
	DESCRIPTION
	"Failed counter updates"
	INDEX { psmProvisionerFailedCounterUpdatesLevelName }
	::={ psmProvisionerFailedCounterUpdatesLevelTable 1 }

PsmProvisionerFailedCounterUpdatesLevelEntry ::=
	SEQUENCE {
		psmProvisionerFailedCounterUpdatesLevelName DisplayString,
		psmProvisionerFailedCounterUpdatesLevelVal  Counter64,
		psmProvisionerFailedCounterUpdatesLevelMom  CounterBasedGauge64,
		psmProvisionerFailedCounterUpdatesLevelMax  CounterBasedGauge64
	}

psmProvisionerFailedCounterUpdatesLevelName OBJECT-TYPE
	SYNTAX      DisplayString
	MAX-ACCESS  not-accessible
	STATUS      current
	DESCRIPTION
	"Failed counter updates"
	::={ psmProvisionerFailedCounterUpdatesLevelEntry 1}

psmProvisionerFailedCounterUpdatesLevelVal OBJECT-TYPE
	SYNTAX     Counter64
	MAX-ACCESS read-only
	STATUS     current
	DESCRIPTION
	"Failed counter updates"
	::={ psmProvisionerFailedCounterUpdatesLevelEntry 2 }

psmProvisionerFailedCounterUpdatesLevelMom OBJECT-TYPE
	SYNTAX     CounterBasedGauge64
	MAX-ACCESS read-only
	STATUS     current
	DESCRIPTION
	"Failed counter updates"
	::={ psmProvisionerFailedCounterUpdatesLevelEntry 3 }

psmProvisionerFailedCounterUpdatesLevelMax OBJECT-TYPE
	SYNTAX     CounterBasedGauge64
	MAX-ACCESS read-only
	STATUS     current
	DESCRIPTION
	"Failed counter updates"
	::={ psmProvisionerFailedCounterUpdatesLevelEntry 4 }

psmProvisionerLastAccountingNormal OBJECT IDENTIFIER ::= { psmProvisioner 6 }

psmProvisionerLastAccountingNormalVal OBJECT-TYPE
	SYNTAX     DateAndTime
	MAX-ACCESS read-only
	STATUS     current
	DESCRIPTION "Last accounting normal"

	::={ psmProvisionerLastAccountingNormal 1 }

psmProvisionerLastAccountingNormalLevelTable OBJECT-TYPE
	SYNTAX     SEQUENCE OF PsmProvisionerLastAccountingNormalLevelEntry
	MAX-ACCESS not-accessible
	STATUS     current
	DESCRIPTION
	"Last accounting normal"
	::={ psmProvisionerLastAccountingNormal 4 }

psmProvisionerLastAccountingNormalLevelEntry OBJECT-TYPE
	SYNTAX      PsmProvisionerLastAccountingNormalLevelEntry
	MAX-ACCESS  not-accessible
	STATUS      current
	DESCRIPTION
	"Last accounting normal"
	INDEX { psmProvisionerLastAccountingNormalLevelName }
	::={ psmProvisionerLastAccountingNormalLevelTable 1 }

PsmProvisionerLastAccountingNormalLevelEntry ::=
	SEQUENCE {
		psmProvisionerLastAccountingNormalLevelName DisplayString,
		psmProvisionerLastAccountingNormalLevelVal  DateAndTime
	}

psmProvisionerLastAccountingNormalLevelName OBJECT-TYPE
	SYNTAX      DisplayString
	MAX-ACCESS  not-accessible
	STATUS      current
	DESCRIPTION
	"Last accounting normal"
	::={ psmProvisionerLastAccountingNormalLevelEntry 1}

psmProvisionerLastAccountingNormalLevelVal OBJECT-TYPE
	SYNTAX     DateAndTime
	MAX-ACCESS read-only
	STATUS     current
	DESCRIPTION
	"Last accounting normal"
	::={ psmProvisionerLastAccountingNormalLevelEntry 2 }

psmProvisionerLastAccountingResendRequested OBJECT IDENTIFIER ::= { psmProvisioner 7 }

psmProvisionerLastAccountingResendRequestedVal OBJECT-TYPE
	SYNTAX     DateAndTime
	MAX-ACCESS read-only
	STATUS     current
	DESCRIPTION "Last accounting resend requested"

	::={ psmProvisionerLastAccountingResendRequested 1 }

psmProvisionerLastAccountingResendRequestedLevelTable OBJECT-TYPE
	SYNTAX     SEQUENCE OF PsmProvisionerLastAccountingResendRequestedLevelEntry
	MAX-ACCESS not-accessible
	STATUS     current
	DESCRIPTION
	"Last accounting resend requested"
	::={ psmProvisionerLastAccountingResendRequested 4 }

psmProvisionerLastAccountingResendRequestedLevelEntry OBJECT-TYPE
	SYNTAX      PsmProvisionerLastAccountingResendRequestedLevelEntry
	MAX-ACCESS  not-accessible
	STATUS      current
	DESCRIPTION
	"Last accounting resend requested"
	INDEX { psmProvisionerLastAccountingResendRequestedLevelName }
	::={ psmProvisionerLastAccountingResendRequestedLevelTable 1 }

PsmProvisionerLastAccountingResendRequestedLevelEntry ::=
	SEQUENCE {
		psmProvisionerLastAccountingResendRequestedLevelName DisplayString,
		psmProvisionerLastAccountingResendRequestedLevelVal  DateAndTime
	}

psmProvisionerLastAccountingResendRequestedLevelName OBJECT-TYPE
	SYNTAX      DisplayString
	MAX-ACCESS  not-accessible
	STATUS      current
	DESCRIPTION
	"Last accounting resend requested"
	::={ psmProvisionerLastAccountingResendRequestedLevelEntry 1}

psmProvisionerLastAccountingResendRequestedLevelVal OBJECT-TYPE
	SYNTAX     DateAndTime
	MAX-ACCESS read-only
	STATUS     current
	DESCRIPTION
	"Last accounting resend requested"
	::={ psmProvisionerLastAccountingResendRequestedLevelEntry 2 }

psmProvisionerLastAccountingUpdatesDropped OBJECT IDENTIFIER ::= { psmProvisioner 8 }

psmProvisionerLastAccountingUpdatesDroppedVal OBJECT-TYPE
	SYNTAX     DateAndTime
	MAX-ACCESS read-only
	STATUS     current
	DESCRIPTION "Last accounting updates dropped"

	::={ psmProvisionerLastAccountingUpdatesDropped 1 }

psmProvisionerLastAccountingUpdatesDroppedLevelTable OBJECT-TYPE
	SYNTAX     SEQUENCE OF PsmProvisionerLastAccountingUpdatesDroppedLevelEntry
	MAX-ACCESS not-accessible
	STATUS     current
	DESCRIPTION
	"Last accounting updates dropped"
	::={ psmProvisionerLastAccountingUpdatesDropped 4 }

psmProvisionerLastAccountingUpdatesDroppedLevelEntry OBJECT-TYPE
	SYNTAX      PsmProvisionerLastAccountingUpdatesDroppedLevelEntry
	MAX-ACCESS  not-accessible
	STATUS      current
	DESCRIPTION
	"Last accounting updates dropped"
	INDEX { psmProvisionerLastAccountingUpdatesDroppedLevelName }
	::={ psmProvisionerLastAccountingUpdatesDroppedLevelTable 1 }

PsmProvisionerLastAccountingUpdatesDroppedLevelEntry ::=
	SEQUENCE {
		psmProvisionerLastAccountingUpdatesDroppedLevelName DisplayString,
		psmProvisionerLastAccountingUpdatesDroppedLevelVal  DateAndTime
	}

psmProvisionerLastAccountingUpdatesDroppedLevelName OBJECT-TYPE
	SYNTAX      DisplayString
	MAX-ACCESS  not-accessible
	STATUS      current
	DESCRIPTION
	"Last accounting updates dropped"
	::={ psmProvisionerLastAccountingUpdatesDroppedLevelEntry 1}

psmProvisionerLastAccountingUpdatesDroppedLevelVal OBJECT-TYPE
	SYNTAX     DateAndTime
	MAX-ACCESS read-only
	STATUS     current
	DESCRIPTION
	"Last accounting updates dropped"
	::={ psmProvisionerLastAccountingUpdatesDroppedLevelEntry 2 }

psmProvisionerLastConnectAttempt OBJECT IDENTIFIER ::= { psmProvisioner 9 }

psmProvisionerLastConnectAttemptVal OBJECT-TYPE
	SYNTAX     DateAndTime
	MAX-ACCESS read-only
	STATUS     current
	DESCRIPTION "Last connect attempt"

	::={ psmProvisionerLastConnectAttempt 1 }

psmProvisionerLastConnectAttemptLevelTable OBJECT-TYPE
	SYNTAX     SEQUENCE OF PsmProvisionerLastConnectAttemptLevelEntry
	MAX-ACCESS not-accessible
	STATUS     current
	DESCRIPTION
	"Last connect attempt"
	::={ psmProvisionerLastConnectAttempt 4 }

psmProvisionerLastConnectAttemptLevelEntry OBJECT-TYPE
	SYNTAX      PsmProvisionerLastConnectAttemptLevelEntry
	MAX-ACCESS  not-accessible
	STATUS      current
	DESCRIPTION
	"Last connect attempt"
	INDEX { psmProvisionerLastConnectAttemptLevelName }
	::={ psmProvisionerLastConnectAttemptLevelTable 1 }

PsmProvisionerLastConnectAttemptLevelEntry ::=
	SEQUENCE {
		psmProvisionerLastConnectAttemptLevelName DisplayString,
		psmProvisionerLastConnectAttemptLevelVal  DateAndTime
	}

psmProvisionerLastConnectAttemptLevelName OBJECT-TYPE
	SYNTAX      DisplayString
	MAX-ACCESS  not-accessible
	STATUS      current
	DESCRIPTION
	"Last connect attempt"
	::={ psmProvisionerLastConnectAttemptLevelEntry 1}

psmProvisionerLastConnectAttemptLevelVal OBJECT-TYPE
	SYNTAX     DateAndTime
	MAX-ACCESS read-only
	STATUS     current
	DESCRIPTION
	"Last connect attempt"
	::={ psmProvisionerLastConnectAttemptLevelEntry 2 }

psmProvisionerLastDisconnected OBJECT IDENTIFIER ::= { psmProvisioner 10 }

psmProvisionerLastDisconnectedVal OBJECT-TYPE
	SYNTAX     DateAndTime
	MAX-ACCESS read-only
	STATUS     current
	DESCRIPTION "Last disconnected"

	::={ psmProvisionerLastDisconnected 1 }

psmProvisionerLastDisconnectedLevelTable OBJECT-TYPE
	SYNTAX     SEQUENCE OF PsmProvisionerLastDisconnectedLevelEntry
	MAX-ACCESS not-accessible
	STATUS     current
	DESCRIPTION
	"Last disconnected"
	::={ psmProvisionerLastDisconnected 4 }

psmProvisionerLastDisconnectedLevelEntry OBJECT-TYPE
	SYNTAX      PsmProvisionerLastDisconnectedLevelEntry
	MAX-ACCESS  not-accessible
	STATUS      current
	DESCRIPTION
	"Last disconnected"
	INDEX { psmProvisionerLastDisconnectedLevelName }
	::={ psmProvisionerLastDisconnectedLevelTable 1 }

PsmProvisionerLastDisconnectedLevelEntry ::=
	SEQUENCE {
		psmProvisionerLastDisconnectedLevelName DisplayString,
		psmProvisionerLastDisconnectedLevelVal  DateAndTime
	}

psmProvisionerLastDisconnectedLevelName OBJECT-TYPE
	SYNTAX      DisplayString
	MAX-ACCESS  not-accessible
	STATUS      current
	DESCRIPTION
	"Last disconnected"
	::={ psmProvisionerLastDisconnectedLevelEntry 1}

psmProvisionerLastDisconnectedLevelVal OBJECT-TYPE
	SYNTAX     DateAndTime
	MAX-ACCESS read-only
	STATUS     current
	DESCRIPTION
	"Last disconnected"
	::={ psmProvisionerLastDisconnectedLevelEntry 2 }

psmProvisionerLastNegotiationAttempt OBJECT IDENTIFIER ::= { psmProvisioner 11 }

psmProvisionerLastNegotiationAttemptVal OBJECT-TYPE
	SYNTAX     DateAndTime
	MAX-ACCESS read-only
	STATUS     current
	DESCRIPTION "Last negotiation attempt"

	::={ psmProvisionerLastNegotiationAttempt 1 }

psmProvisionerLastNegotiationAttemptLevelTable OBJECT-TYPE
	SYNTAX     SEQUENCE OF PsmProvisionerLastNegotiationAttemptLevelEntry
	MAX-ACCESS not-accessible
	STATUS     current
	DESCRIPTION
	"Last negotiation attempt"
	::={ psmProvisionerLastNegotiationAttempt 4 }

psmProvisionerLastNegotiationAttemptLevelEntry OBJECT-TYPE
	SYNTAX      PsmProvisionerLastNegotiationAttemptLevelEntry
	MAX-ACCESS  not-accessible
	STATUS      current
	DESCRIPTION
	"Last negotiation attempt"
	INDEX { psmProvisionerLastNegotiationAttemptLevelName }
	::={ psmProvisionerLastNegotiationAttemptLevelTable 1 }

PsmProvisionerLastNegotiationAttemptLevelEntry ::=
	SEQUENCE {
		psmProvisionerLastNegotiationAttemptLevelName DisplayString,
		psmProvisionerLastNegotiationAttemptLevelVal  DateAndTime
	}

psmProvisionerLastNegotiationAttemptLevelName OBJECT-TYPE
	SYNTAX      DisplayString
	MAX-ACCESS  not-accessible
	STATUS      current
	DESCRIPTION
	"Last negotiation attempt"
	::={ psmProvisionerLastNegotiationAttemptLevelEntry 1}

psmProvisionerLastNegotiationAttemptLevelVal OBJECT-TYPE
	SYNTAX     DateAndTime
	MAX-ACCESS read-only
	STATUS     current
	DESCRIPTION
	"Last negotiation attempt"
	::={ psmProvisionerLastNegotiationAttemptLevelEntry 2 }

psmProvisionerLastOnline OBJECT IDENTIFIER ::= { psmProvisioner 12 }

psmProvisionerLastOnlineVal OBJECT-TYPE
	SYNTAX     DateAndTime
	MAX-ACCESS read-only
	STATUS     current
	DESCRIPTION "Last online"

	::={ psmProvisionerLastOnline 1 }

psmProvisionerLastOnlineLevelTable OBJECT-TYPE
	SYNTAX     SEQUENCE OF PsmProvisionerLastOnlineLevelEntry
	MAX-ACCESS not-accessible
	STATUS     current
	DESCRIPTION
	"Last online"
	::={ psmProvisionerLastOnline 4 }

psmProvisionerLastOnlineLevelEntry OBJECT-TYPE
	SYNTAX      PsmProvisionerLastOnlineLevelEntry
	MAX-ACCESS  not-accessible
	STATUS      current
	DESCRIPTION
	"Last online"
	INDEX { psmProvisionerLastOnlineLevelName }
	::={ psmProvisionerLastOnlineLevelTable 1 }

PsmProvisionerLastOnlineLevelEntry ::=
	SEQUENCE {
		psmProvisionerLastOnlineLevelName DisplayString,
		psmProvisionerLastOnlineLevelVal  DateAndTime
	}

psmProvisionerLastOnlineLevelName OBJECT-TYPE
	SYNTAX      DisplayString
	MAX-ACCESS  not-accessible
	STATUS      current
	DESCRIPTION
	"Last online"
	::={ psmProvisionerLastOnlineLevelEntry 1}

psmProvisionerLastOnlineLevelVal OBJECT-TYPE
	SYNTAX     DateAndTime
	MAX-ACCESS read-only
	STATUS     current
	DESCRIPTION
	"Last online"
	::={ psmProvisionerLastOnlineLevelEntry 2 }

psmProvisionerLastSyncAttempt OBJECT IDENTIFIER ::= { psmProvisioner 13 }

psmProvisionerLastSyncAttemptVal OBJECT-TYPE
	SYNTAX     DateAndTime
	MAX-ACCESS read-only
	STATUS     current
	DESCRIPTION "Last sync attempt"

	::={ psmProvisionerLastSyncAttempt 1 }

psmProvisionerLastSyncAttemptLevelTable OBJECT-TYPE
	SYNTAX     SEQUENCE OF PsmProvisionerLastSyncAttemptLevelEntry
	MAX-ACCESS not-accessible
	STATUS     current
	DESCRIPTION
	"Last sync attempt"
	::={ psmProvisionerLastSyncAttempt 4 }

psmProvisionerLastSyncAttemptLevelEntry OBJECT-TYPE
	SYNTAX      PsmProvisionerLastSyncAttemptLevelEntry
	MAX-ACCESS  not-accessible
	STATUS      current
	DESCRIPTION
	"Last sync attempt"
	INDEX { psmProvisionerLastSyncAttemptLevelName }
	::={ psmProvisionerLastSyncAttemptLevelTable 1 }

PsmProvisionerLastSyncAttemptLevelEntry ::=
	SEQUENCE {
		psmProvisionerLastSyncAttemptLevelName DisplayString,
		psmProvisionerLastSyncAttemptLevelVal  DateAndTime
	}

psmProvisionerLastSyncAttemptLevelName OBJECT-TYPE
	SYNTAX      DisplayString
	MAX-ACCESS  not-accessible
	STATUS      current
	DESCRIPTION
	"Last sync attempt"
	::={ psmProvisionerLastSyncAttemptLevelEntry 1}

psmProvisionerLastSyncAttemptLevelVal OBJECT-TYPE
	SYNTAX     DateAndTime
	MAX-ACCESS read-only
	STATUS     current
	DESCRIPTION
	"Last sync attempt"
	::={ psmProvisionerLastSyncAttemptLevelEntry 2 }

psmProvisionerReceivedAccounting OBJECT IDENTIFIER ::= { psmProvisioner 14 }

psmProvisionerReceivedAccountingVal OBJECT-TYPE
	SYNTAX     Counter64
	MAX-ACCESS read-only
	STATUS     current
	DESCRIPTION "Received accounting"

	::={ psmProvisionerReceivedAccounting 1 }

psmProvisionerReceivedAccountingMom OBJECT-TYPE
	SYNTAX     CounterBasedGauge64
	MAX-ACCESS read-only
	STATUS     current
	DESCRIPTION "Received accounting"

	::={ psmProvisionerReceivedAccounting 2 }

psmProvisionerReceivedAccountingMax OBJECT-TYPE
	SYNTAX     CounterBasedGauge64
	MAX-ACCESS read-only
	STATUS     current
	DESCRIPTION "Received accounting"

	::={ psmProvisionerReceivedAccounting 3 }

psmProvisionerReceivedAccountingLevelTable OBJECT-TYPE
	SYNTAX     SEQUENCE OF PsmProvisionerReceivedAccountingLevelEntry
	MAX-ACCESS not-accessible
	STATUS     current
	DESCRIPTION
	"Received accounting"
	::={ psmProvisionerReceivedAccounting 4 }

psmProvisionerReceivedAccountingLevelEntry OBJECT-TYPE
	SYNTAX      PsmProvisionerReceivedAccountingLevelEntry
	MAX-ACCESS  not-accessible
	STATUS      current
	DESCRIPTION
	"Received accounting"
	INDEX { psmProvisionerReceivedAccountingLevelName }
	::={ psmProvisionerReceivedAccountingLevelTable 1 }

PsmProvisionerReceivedAccountingLevelEntry ::=
	SEQUENCE {
		psmProvisionerReceivedAccountingLevelName DisplayString,
		psmProvisionerReceivedAccountingLevelVal  Counter64,
		psmProvisionerReceivedAccountingLevelMom  CounterBasedGauge64,
		psmProvisionerReceivedAccountingLevelMax  CounterBasedGauge64
	}

psmProvisionerReceivedAccountingLevelName OBJECT-TYPE
	SYNTAX      DisplayString
	MAX-ACCESS  not-accessible
	STATUS      current
	DESCRIPTION
	"Received accounting"
	::={ psmProvisionerReceivedAccountingLevelEntry 1}

psmProvisionerReceivedAccountingLevelVal OBJECT-TYPE
	SYNTAX     Counter64
	MAX-ACCESS read-only
	STATUS     current
	DESCRIPTION
	"Received accounting"
	::={ psmProvisionerReceivedAccountingLevelEntry 2 }

psmProvisionerReceivedAccountingLevelMom OBJECT-TYPE
	SYNTAX     CounterBasedGauge64
	MAX-ACCESS read-only
	STATUS     current
	DESCRIPTION
	"Received accounting"
	::={ psmProvisionerReceivedAccountingLevelEntry 3 }

psmProvisionerReceivedAccountingLevelMax OBJECT-TYPE
	SYNTAX     CounterBasedGauge64
	MAX-ACCESS read-only
	STATUS     current
	DESCRIPTION
	"Received accounting"
	::={ psmProvisionerReceivedAccountingLevelEntry 4 }

psmProvisionerReconnects OBJECT IDENTIFIER ::= { psmProvisioner 15 }

psmProvisionerReconnectsVal OBJECT-TYPE
	SYNTAX     Counter64
	MAX-ACCESS read-only
	STATUS     current
	DESCRIPTION "Reconnects"

	::={ psmProvisionerReconnects 1 }

psmProvisionerReconnectsMom OBJECT-TYPE
	SYNTAX     CounterBasedGauge64
	MAX-ACCESS read-only
	STATUS     current
	DESCRIPTION "Reconnects"

	::={ psmProvisionerReconnects 2 }

psmProvisionerReconnectsMax OBJECT-TYPE
	SYNTAX     CounterBasedGauge64
	MAX-ACCESS read-only
	STATUS     current
	DESCRIPTION "Reconnects"

	::={ psmProvisionerReconnects 3 }

psmProvisionerReconnectsLevelTable OBJECT-TYPE
	SYNTAX     SEQUENCE OF PsmProvisionerReconnectsLevelEntry
	MAX-ACCESS not-accessible
	STATUS     current
	DESCRIPTION
	"Reconnects"
	::={ psmProvisionerReconnects 4 }

psmProvisionerReconnectsLevelEntry OBJECT-TYPE
	SYNTAX      PsmProvisionerReconnectsLevelEntry
	MAX-ACCESS  not-accessible
	STATUS      current
	DESCRIPTION
	"Reconnects"
	INDEX { psmProvisionerReconnectsLevelName }
	::={ psmProvisionerReconnectsLevelTable 1 }

PsmProvisionerReconnectsLevelEntry ::=
	SEQUENCE {
		psmProvisionerReconnectsLevelName DisplayString,
		psmProvisionerReconnectsLevelVal  Counter64,
		psmProvisionerReconnectsLevelMom  CounterBasedGauge64,
		psmProvisionerReconnectsLevelMax  CounterBasedGauge64
	}

psmProvisionerReconnectsLevelName OBJECT-TYPE
	SYNTAX      DisplayString
	MAX-ACCESS  not-accessible
	STATUS      current
	DESCRIPTION
	"Reconnects"
	::={ psmProvisionerReconnectsLevelEntry 1}

psmProvisionerReconnectsLevelVal OBJECT-TYPE
	SYNTAX     Counter64
	MAX-ACCESS read-only
	STATUS     current
	DESCRIPTION
	"Reconnects"
	::={ psmProvisionerReconnectsLevelEntry 2 }

psmProvisionerReconnectsLevelMom OBJECT-TYPE
	SYNTAX     CounterBasedGauge64
	MAX-ACCESS read-only
	STATUS     current
	DESCRIPTION
	"Reconnects"
	::={ psmProvisionerReconnectsLevelEntry 3 }

psmProvisionerReconnectsLevelMax OBJECT-TYPE
	SYNTAX     CounterBasedGauge64
	MAX-ACCESS read-only
	STATUS     current
	DESCRIPTION
	"Reconnects"
	::={ psmProvisionerReconnectsLevelEntry 4 }

psmProvisionerSentObjectcreate OBJECT IDENTIFIER ::= { psmProvisioner 16 }

psmProvisionerSentObjectcreateVal OBJECT-TYPE
	SYNTAX     Counter64
	MAX-ACCESS read-only
	STATUS     current
	DESCRIPTION "Sent object-create"

	::={ psmProvisionerSentObjectcreate 1 }

psmProvisionerSentObjectcreateMom OBJECT-TYPE
	SYNTAX     CounterBasedGauge64
	MAX-ACCESS read-only
	STATUS     current
	DESCRIPTION "Sent object-create"

	::={ psmProvisionerSentObjectcreate 2 }

psmProvisionerSentObjectcreateMax OBJECT-TYPE
	SYNTAX     CounterBasedGauge64
	MAX-ACCESS read-only
	STATUS     current
	DESCRIPTION "Sent object-create"

	::={ psmProvisionerSentObjectcreate 3 }

psmProvisionerSentObjectcreateLevelTable OBJECT-TYPE
	SYNTAX     SEQUENCE OF PsmProvisionerSentObjectcreateLevelEntry
	MAX-ACCESS not-accessible
	STATUS     current
	DESCRIPTION
	"Sent object-create"
	::={ psmProvisionerSentObjectcreate 4 }

psmProvisionerSentObjectcreateLevelEntry OBJECT-TYPE
	SYNTAX      PsmProvisionerSentObjectcreateLevelEntry
	MAX-ACCESS  not-accessible
	STATUS      current
	DESCRIPTION
	"Sent object-create"
	INDEX { psmProvisionerSentObjectcreateLevelName }
	::={ psmProvisionerSentObjectcreateLevelTable 1 }

PsmProvisionerSentObjectcreateLevelEntry ::=
	SEQUENCE {
		psmProvisionerSentObjectcreateLevelName DisplayString,
		psmProvisionerSentObjectcreateLevelVal  Counter64,
		psmProvisionerSentObjectcreateLevelMom  CounterBasedGauge64,
		psmProvisionerSentObjectcreateLevelMax  CounterBasedGauge64
	}

psmProvisionerSentObjectcreateLevelName OBJECT-TYPE
	SYNTAX      DisplayString
	MAX-ACCESS  not-accessible
	STATUS      current
	DESCRIPTION
	"Sent object-create"
	::={ psmProvisionerSentObjectcreateLevelEntry 1}

psmProvisionerSentObjectcreateLevelVal OBJECT-TYPE
	SYNTAX     Counter64
	MAX-ACCESS read-only
	STATUS     current
	DESCRIPTION
	"Sent object-create"
	::={ psmProvisionerSentObjectcreateLevelEntry 2 }

psmProvisionerSentObjectcreateLevelMom OBJECT-TYPE
	SYNTAX     CounterBasedGauge64
	MAX-ACCESS read-only
	STATUS     current
	DESCRIPTION
	"Sent object-create"
	::={ psmProvisionerSentObjectcreateLevelEntry 3 }

psmProvisionerSentObjectcreateLevelMax OBJECT-TYPE
	SYNTAX     CounterBasedGauge64
	MAX-ACCESS read-only
	STATUS     current
	DESCRIPTION
	"Sent object-create"
	::={ psmProvisionerSentObjectcreateLevelEntry 4 }

psmProvisionerSentObjectdelete OBJECT IDENTIFIER ::= { psmProvisioner 17 }

psmProvisionerSentObjectdeleteVal OBJECT-TYPE
	SYNTAX     Counter64
	MAX-ACCESS read-only
	STATUS     current
	DESCRIPTION "Sent object-delete"

	::={ psmProvisionerSentObjectdelete 1 }

psmProvisionerSentObjectdeleteMom OBJECT-TYPE
	SYNTAX     CounterBasedGauge64
	MAX-ACCESS read-only
	STATUS     current
	DESCRIPTION "Sent object-delete"

	::={ psmProvisionerSentObjectdelete 2 }

psmProvisionerSentObjectdeleteMax OBJECT-TYPE
	SYNTAX     CounterBasedGauge64
	MAX-ACCESS read-only
	STATUS     current
	DESCRIPTION "Sent object-delete"

	::={ psmProvisionerSentObjectdelete 3 }

psmProvisionerSentObjectdeleteLevelTable OBJECT-TYPE
	SYNTAX     SEQUENCE OF PsmProvisionerSentObjectdeleteLevelEntry
	MAX-ACCESS not-accessible
	STATUS     current
	DESCRIPTION
	"Sent object-delete"
	::={ psmProvisionerSentObjectdelete 4 }

psmProvisionerSentObjectdeleteLevelEntry OBJECT-TYPE
	SYNTAX      PsmProvisionerSentObjectdeleteLevelEntry
	MAX-ACCESS  not-accessible
	STATUS      current
	DESCRIPTION
	"Sent object-delete"
	INDEX { psmProvisionerSentObjectdeleteLevelName }
	::={ psmProvisionerSentObjectdeleteLevelTable 1 }

PsmProvisionerSentObjectdeleteLevelEntry ::=
	SEQUENCE {
		psmProvisionerSentObjectdeleteLevelName DisplayString,
		psmProvisionerSentObjectdeleteLevelVal  Counter64,
		psmProvisionerSentObjectdeleteLevelMom  CounterBasedGauge64,
		psmProvisionerSentObjectdeleteLevelMax  CounterBasedGauge64
	}

psmProvisionerSentObjectdeleteLevelName OBJECT-TYPE
	SYNTAX      DisplayString
	MAX-ACCESS  not-accessible
	STATUS      current
	DESCRIPTION
	"Sent object-delete"
	::={ psmProvisionerSentObjectdeleteLevelEntry 1}

psmProvisionerSentObjectdeleteLevelVal OBJECT-TYPE
	SYNTAX     Counter64
	MAX-ACCESS read-only
	STATUS     current
	DESCRIPTION
	"Sent object-delete"
	::={ psmProvisionerSentObjectdeleteLevelEntry 2 }

psmProvisionerSentObjectdeleteLevelMom OBJECT-TYPE
	SYNTAX     CounterBasedGauge64
	MAX-ACCESS read-only
	STATUS     current
	DESCRIPTION
	"Sent object-delete"
	::={ psmProvisionerSentObjectdeleteLevelEntry 3 }

psmProvisionerSentObjectdeleteLevelMax OBJECT-TYPE
	SYNTAX     CounterBasedGauge64
	MAX-ACCESS read-only
	STATUS     current
	DESCRIPTION
	"Sent object-delete"
	::={ psmProvisionerSentObjectdeleteLevelEntry 4 }

psmProvisionerSentObjectdelta OBJECT IDENTIFIER ::= { psmProvisioner 18 }

psmProvisionerSentObjectdeltaVal OBJECT-TYPE
	SYNTAX     Counter64
	MAX-ACCESS read-only
	STATUS     current
	DESCRIPTION "Sent object-delta"

	::={ psmProvisionerSentObjectdelta 1 }

psmProvisionerSentObjectdeltaMom OBJECT-TYPE
	SYNTAX     CounterBasedGauge64
	MAX-ACCESS read-only
	STATUS     current
	DESCRIPTION "Sent object-delta"

	::={ psmProvisionerSentObjectdelta 2 }

psmProvisionerSentObjectdeltaMax OBJECT-TYPE
	SYNTAX     CounterBasedGauge64
	MAX-ACCESS read-only
	STATUS     current
	DESCRIPTION "Sent object-delta"

	::={ psmProvisionerSentObjectdelta 3 }

psmProvisionerSentObjectdeltaLevelTable OBJECT-TYPE
	SYNTAX     SEQUENCE OF PsmProvisionerSentObjectdeltaLevelEntry
	MAX-ACCESS not-accessible
	STATUS     current
	DESCRIPTION
	"Sent object-delta"
	::={ psmProvisionerSentObjectdelta 4 }

psmProvisionerSentObjectdeltaLevelEntry OBJECT-TYPE
	SYNTAX      PsmProvisionerSentObjectdeltaLevelEntry
	MAX-ACCESS  not-accessible
	STATUS      current
	DESCRIPTION
	"Sent object-delta"
	INDEX { psmProvisionerSentObjectdeltaLevelName }
	::={ psmProvisionerSentObjectdeltaLevelTable 1 }

PsmProvisionerSentObjectdeltaLevelEntry ::=
	SEQUENCE {
		psmProvisionerSentObjectdeltaLevelName DisplayString,
		psmProvisionerSentObjectdeltaLevelVal  Counter64,
		psmProvisionerSentObjectdeltaLevelMom  CounterBasedGauge64,
		psmProvisionerSentObjectdeltaLevelMax  CounterBasedGauge64
	}

psmProvisionerSentObjectdeltaLevelName OBJECT-TYPE
	SYNTAX      DisplayString
	MAX-ACCESS  not-accessible
	STATUS      current
	DESCRIPTION
	"Sent object-delta"
	::={ psmProvisionerSentObjectdeltaLevelEntry 1}

psmProvisionerSentObjectdeltaLevelVal OBJECT-TYPE
	SYNTAX     Counter64
	MAX-ACCESS read-only
	STATUS     current
	DESCRIPTION
	"Sent object-delta"
	::={ psmProvisionerSentObjectdeltaLevelEntry 2 }

psmProvisionerSentObjectdeltaLevelMom OBJECT-TYPE
	SYNTAX     CounterBasedGauge64
	MAX-ACCESS read-only
	STATUS     current
	DESCRIPTION
	"Sent object-delta"
	::={ psmProvisionerSentObjectdeltaLevelEntry 3 }

psmProvisionerSentObjectdeltaLevelMax OBJECT-TYPE
	SYNTAX     CounterBasedGauge64
	MAX-ACCESS read-only
	STATUS     current
	DESCRIPTION
	"Sent object-delta"
	::={ psmProvisionerSentObjectdeltaLevelEntry 4 }

psmProvisionerState OBJECT IDENTIFIER ::= { psmProvisioner 19 }

psmProvisionerStateVal OBJECT-TYPE
	SYNTAX     INTEGER {
		disabled(0),
		disconnected(1),
		connecting(2),
		negotiating(3),
		synchronizing(4),
		online(5)
	}
	MAX-ACCESS read-only
	STATUS     current
	DESCRIPTION "State"

	::={ psmProvisionerState 1 }

psmProvisionerStateLevelTable OBJECT-TYPE
	SYNTAX     SEQUENCE OF PsmProvisionerStateLevelEntry
	MAX-ACCESS not-accessible
	STATUS     current
	DESCRIPTION
	"State"
	::={ psmProvisionerState 4 }

psmProvisionerStateLevelEntry OBJECT-TYPE
	SYNTAX      PsmProvisionerStateLevelEntry
	MAX-ACCESS  not-accessible
	STATUS      current
	DESCRIPTION
	"State"
	INDEX { psmProvisionerStateLevelName }
	::={ psmProvisionerStateLevelTable 1 }

PsmProvisionerStateLevelEntry ::=
	SEQUENCE {
		psmProvisionerStateLevelName DisplayString,
		psmProvisionerStateLevelVal  INTEGER
	}

psmProvisionerStateLevelName OBJECT-TYPE
	SYNTAX      DisplayString
	MAX-ACCESS  not-accessible
	STATUS      current
	DESCRIPTION
	"State"
	::={ psmProvisionerStateLevelEntry 1}

psmProvisionerStateLevelVal OBJECT-TYPE
	SYNTAX     INTEGER {
		disabled(0),
		disconnected(1),
		connecting(2),
		negotiating(3),
		synchronizing(4),
		online(5)
	}
	MAX-ACCESS read-only
	STATUS     current
	DESCRIPTION
	"State"
	::={ psmProvisionerStateLevelEntry 2 }

psmStorageCyclic OBJECT IDENTIFIER ::= { psmv2 9 }

psmStorageCyclicTotalBytesWritten OBJECT IDENTIFIER ::= { psmStorageCyclic 1 }

psmStorageCyclicTotalBytesWrittenVal OBJECT-TYPE
	SYNTAX     Counter64
	MAX-ACCESS read-only
	STATUS     current
	DESCRIPTION "Total bytes written"

	::={ psmStorageCyclicTotalBytesWritten 1 }

psmStorageCyclicTotalBytesWrittenMom OBJECT-TYPE
	SYNTAX     CounterBasedGauge64
	MAX-ACCESS read-only
	STATUS     current
	DESCRIPTION "Total bytes written"

	::={ psmStorageCyclicTotalBytesWritten 2 }

psmStorageCyclicTotalBytesWrittenMax OBJECT-TYPE
	SYNTAX     CounterBasedGauge64
	MAX-ACCESS read-only
	STATUS     current
	DESCRIPTION "Total bytes written"

	::={ psmStorageCyclicTotalBytesWritten 3 }

psmStorageCyclicTotalBytesWrittenLevelTable OBJECT-TYPE
	SYNTAX     SEQUENCE OF PsmStorageCyclicTotalBytesWrittenLevelEntry
	MAX-ACCESS not-accessible
	STATUS     current
	DESCRIPTION
	"Total bytes written"
	::={ psmStorageCyclicTotalBytesWritten 4 }

psmStorageCyclicTotalBytesWrittenLevelEntry OBJECT-TYPE
	SYNTAX      PsmStorageCyclicTotalBytesWrittenLevelEntry
	MAX-ACCESS  not-accessible
	STATUS      current
	DESCRIPTION
	"Total bytes written"
	INDEX { psmStorageCyclicTotalBytesWrittenLevelName }
	::={ psmStorageCyclicTotalBytesWrittenLevelTable 1 }

PsmStorageCyclicTotalBytesWrittenLevelEntry ::=
	SEQUENCE {
		psmStorageCyclicTotalBytesWrittenLevelName DisplayString,
		psmStorageCyclicTotalBytesWrittenLevelVal  Counter64,
		psmStorageCyclicTotalBytesWrittenLevelMom  CounterBasedGauge64,
		psmStorageCyclicTotalBytesWrittenLevelMax  CounterBasedGauge64
	}

psmStorageCyclicTotalBytesWrittenLevelName OBJECT-TYPE
	SYNTAX      DisplayString
	MAX-ACCESS  not-accessible
	STATUS      current
	DESCRIPTION
	"Total bytes written"
	::={ psmStorageCyclicTotalBytesWrittenLevelEntry 1}

psmStorageCyclicTotalBytesWrittenLevelVal OBJECT-TYPE
	SYNTAX     Counter64
	MAX-ACCESS read-only
	STATUS     current
	DESCRIPTION
	"Total bytes written"
	::={ psmStorageCyclicTotalBytesWrittenLevelEntry 2 }

psmStorageCyclicTotalBytesWrittenLevelMom OBJECT-TYPE
	SYNTAX     CounterBasedGauge64
	MAX-ACCESS read-only
	STATUS     current
	DESCRIPTION
	"Total bytes written"
	::={ psmStorageCyclicTotalBytesWrittenLevelEntry 3 }

psmStorageCyclicTotalBytesWrittenLevelMax OBJECT-TYPE
	SYNTAX     CounterBasedGauge64
	MAX-ACCESS read-only
	STATUS     current
	DESCRIPTION
	"Total bytes written"
	::={ psmStorageCyclicTotalBytesWrittenLevelEntry 4 }

psmStorageCyclicTotalChangedObjectsWritten OBJECT IDENTIFIER ::= { psmStorageCyclic 2 }

psmStorageCyclicTotalChangedObjectsWrittenVal OBJECT-TYPE
	SYNTAX     Counter64
	MAX-ACCESS read-only
	STATUS     current
	DESCRIPTION "Total changed objects written"

	::={ psmStorageCyclicTotalChangedObjectsWritten 1 }

psmStorageCyclicTotalChangedObjectsWrittenMom OBJECT-TYPE
	SYNTAX     CounterBasedGauge64
	MAX-ACCESS read-only
	STATUS     current
	DESCRIPTION "Total changed objects written"

	::={ psmStorageCyclicTotalChangedObjectsWritten 2 }

psmStorageCyclicTotalChangedObjectsWrittenMax OBJECT-TYPE
	SYNTAX     CounterBasedGauge64
	MAX-ACCESS read-only
	STATUS     current
	DESCRIPTION "Total changed objects written"

	::={ psmStorageCyclicTotalChangedObjectsWritten 3 }

psmStorageCyclicTotalChangedObjectsWrittenLevelTable OBJECT-TYPE
	SYNTAX     SEQUENCE OF PsmStorageCyclicTotalChangedObjectsWrittenLevelEntry
	MAX-ACCESS not-accessible
	STATUS     current
	DESCRIPTION
	"Total changed objects written"
	::={ psmStorageCyclicTotalChangedObjectsWritten 4 }

psmStorageCyclicTotalChangedObjectsWrittenLevelEntry OBJECT-TYPE
	SYNTAX      PsmStorageCyclicTotalChangedObjectsWrittenLevelEntry
	MAX-ACCESS  not-accessible
	STATUS      current
	DESCRIPTION
	"Total changed objects written"
	INDEX { psmStorageCyclicTotalChangedObjectsWrittenLevelName }
	::={ psmStorageCyclicTotalChangedObjectsWrittenLevelTable 1 }

PsmStorageCyclicTotalChangedObjectsWrittenLevelEntry ::=
	SEQUENCE {
		psmStorageCyclicTotalChangedObjectsWrittenLevelName DisplayString,
		psmStorageCyclicTotalChangedObjectsWrittenLevelVal  Counter64,
		psmStorageCyclicTotalChangedObjectsWrittenLevelMom  CounterBasedGauge64,
		psmStorageCyclicTotalChangedObjectsWrittenLevelMax  CounterBasedGauge64
	}

psmStorageCyclicTotalChangedObjectsWrittenLevelName OBJECT-TYPE
	SYNTAX      DisplayString
	MAX-ACCESS  not-accessible
	STATUS      current
	DESCRIPTION
	"Total changed objects written"
	::={ psmStorageCyclicTotalChangedObjectsWrittenLevelEntry 1}

psmStorageCyclicTotalChangedObjectsWrittenLevelVal OBJECT-TYPE
	SYNTAX     Counter64
	MAX-ACCESS read-only
	STATUS     current
	DESCRIPTION
	"Total changed objects written"
	::={ psmStorageCyclicTotalChangedObjectsWrittenLevelEntry 2 }

psmStorageCyclicTotalChangedObjectsWrittenLevelMom OBJECT-TYPE
	SYNTAX     CounterBasedGauge64
	MAX-ACCESS read-only
	STATUS     current
	DESCRIPTION
	"Total changed objects written"
	::={ psmStorageCyclicTotalChangedObjectsWrittenLevelEntry 3 }

psmStorageCyclicTotalChangedObjectsWrittenLevelMax OBJECT-TYPE
	SYNTAX     CounterBasedGauge64
	MAX-ACCESS read-only
	STATUS     current
	DESCRIPTION
	"Total changed objects written"
	::={ psmStorageCyclicTotalChangedObjectsWrittenLevelEntry 4 }

psmStorageCyclicObjectCountOnDisk OBJECT IDENTIFIER ::= { psmStorageCyclic 3 }

psmStorageCyclicObjectCountOnDiskVal OBJECT-TYPE
	SYNTAX     CounterBasedGauge64
	MAX-ACCESS read-only
	STATUS     current
	DESCRIPTION "Object count on disk"

	::={ psmStorageCyclicObjectCountOnDisk 1 }

psmStorageCyclicObjectCountOnDiskMax OBJECT-TYPE
	SYNTAX     CounterBasedGauge64
	MAX-ACCESS read-only
	STATUS     current
	DESCRIPTION "Object count on disk"

	::={ psmStorageCyclicObjectCountOnDisk 3 }

psmStorageCyclicObjectCountOnDiskLevelTable OBJECT-TYPE
	SYNTAX     SEQUENCE OF PsmStorageCyclicObjectCountOnDiskLevelEntry
	MAX-ACCESS not-accessible
	STATUS     current
	DESCRIPTION
	"Object count on disk"
	::={ psmStorageCyclicObjectCountOnDisk 4 }

psmStorageCyclicObjectCountOnDiskLevelEntry OBJECT-TYPE
	SYNTAX      PsmStorageCyclicObjectCountOnDiskLevelEntry
	MAX-ACCESS  not-accessible
	STATUS      current
	DESCRIPTION
	"Object count on disk"
	INDEX { psmStorageCyclicObjectCountOnDiskLevelName }
	::={ psmStorageCyclicObjectCountOnDiskLevelTable 1 }

PsmStorageCyclicObjectCountOnDiskLevelEntry ::=
	SEQUENCE {
		psmStorageCyclicObjectCountOnDiskLevelName DisplayString,
		psmStorageCyclicObjectCountOnDiskLevelVal  CounterBasedGauge64,
		psmStorageCyclicObjectCountOnDiskLevelMax  CounterBasedGauge64
	}

psmStorageCyclicObjectCountOnDiskLevelName OBJECT-TYPE
	SYNTAX      DisplayString
	MAX-ACCESS  not-accessible
	STATUS      current
	DESCRIPTION
	"Object count on disk"
	::={ psmStorageCyclicObjectCountOnDiskLevelEntry 1}

psmStorageCyclicObjectCountOnDiskLevelVal OBJECT-TYPE
	SYNTAX     CounterBasedGauge64
	MAX-ACCESS read-only
	STATUS     current
	DESCRIPTION
	"Object count on disk"
	::={ psmStorageCyclicObjectCountOnDiskLevelEntry 2 }

psmStorageCyclicObjectCountOnDiskLevelMax OBJECT-TYPE
	SYNTAX     CounterBasedGauge64
	MAX-ACCESS read-only
	STATUS     current
	DESCRIPTION
	"Object count on disk"
	::={ psmStorageCyclicObjectCountOnDiskLevelEntry 4 }

psmStorageCyclicDisktomemoryObjectRatio OBJECT IDENTIFIER ::= { psmStorageCyclic 4 }

psmStorageCyclicDisktomemoryObjectRatioVal OBJECT-TYPE
	SYNTAX     CounterBasedGauge64
	MAX-ACCESS read-only
	STATUS     current
	DESCRIPTION "Disk-to-memory object ratio (%)"

	::={ psmStorageCyclicDisktomemoryObjectRatio 1 }

psmStorageCyclicDisktomemoryObjectRatioMax OBJECT-TYPE
	SYNTAX     CounterBasedGauge64
	MAX-ACCESS read-only
	STATUS     current
	DESCRIPTION "Disk-to-memory object ratio (%)"

	::={ psmStorageCyclicDisktomemoryObjectRatio 3 }

psmStorageCyclicDisktomemoryObjectRatioLevelTable OBJECT-TYPE
	SYNTAX     SEQUENCE OF PsmStorageCyclicDisktomemoryObjectRatioLevelEntry
	MAX-ACCESS not-accessible
	STATUS     current
	DESCRIPTION
	"Disk-to-memory object ratio (%)"
	::={ psmStorageCyclicDisktomemoryObjectRatio 4 }

psmStorageCyclicDisktomemoryObjectRatioLevelEntry OBJECT-TYPE
	SYNTAX      PsmStorageCyclicDisktomemoryObjectRatioLevelEntry
	MAX-ACCESS  not-accessible
	STATUS      current
	DESCRIPTION
	"Disk-to-memory object ratio (%)"
	INDEX { psmStorageCyclicDisktomemoryObjectRatioLevelName }
	::={ psmStorageCyclicDisktomemoryObjectRatioLevelTable 1 }

PsmStorageCyclicDisktomemoryObjectRatioLevelEntry ::=
	SEQUENCE {
		psmStorageCyclicDisktomemoryObjectRatioLevelName DisplayString,
		psmStorageCyclicDisktomemoryObjectRatioLevelVal  CounterBasedGauge64,
		psmStorageCyclicDisktomemoryObjectRatioLevelMax  CounterBasedGauge64
	}

psmStorageCyclicDisktomemoryObjectRatioLevelName OBJECT-TYPE
	SYNTAX      DisplayString
	MAX-ACCESS  not-accessible
	STATUS      current
	DESCRIPTION
	"Disk-to-memory object ratio (%)"
	::={ psmStorageCyclicDisktomemoryObjectRatioLevelEntry 1}

psmStorageCyclicDisktomemoryObjectRatioLevelVal OBJECT-TYPE
	SYNTAX     CounterBasedGauge64
	MAX-ACCESS read-only
	STATUS     current
	DESCRIPTION
	"Disk-to-memory object ratio (%)"
	::={ psmStorageCyclicDisktomemoryObjectRatioLevelEntry 2 }

psmStorageCyclicDisktomemoryObjectRatioLevelMax OBJECT-TYPE
	SYNTAX     CounterBasedGauge64
	MAX-ACCESS read-only
	STATUS     current
	DESCRIPTION
	"Disk-to-memory object ratio (%)"
	::={ psmStorageCyclicDisktomemoryObjectRatioLevelEntry 4 }

psmStorageCyclicMaxFileCount OBJECT IDENTIFIER ::= { psmStorageCyclic 5 }

psmStorageCyclicMaxFileCountVal OBJECT-TYPE
	SYNTAX     CounterBasedGauge64
	MAX-ACCESS read-only
	STATUS     current
	DESCRIPTION "Max file count"

	::={ psmStorageCyclicMaxFileCount 1 }

psmStorageCyclicMaxFileCountMax OBJECT-TYPE
	SYNTAX     CounterBasedGauge64
	MAX-ACCESS read-only
	STATUS     current
	DESCRIPTION "Max file count"

	::={ psmStorageCyclicMaxFileCount 3 }

psmStorageCyclicMaxFileCountLevelTable OBJECT-TYPE
	SYNTAX     SEQUENCE OF PsmStorageCyclicMaxFileCountLevelEntry
	MAX-ACCESS not-accessible
	STATUS     current
	DESCRIPTION
	"Max file count"
	::={ psmStorageCyclicMaxFileCount 4 }

psmStorageCyclicMaxFileCountLevelEntry OBJECT-TYPE
	SYNTAX      PsmStorageCyclicMaxFileCountLevelEntry
	MAX-ACCESS  not-accessible
	STATUS      current
	DESCRIPTION
	"Max file count"
	INDEX { psmStorageCyclicMaxFileCountLevelName }
	::={ psmStorageCyclicMaxFileCountLevelTable 1 }

PsmStorageCyclicMaxFileCountLevelEntry ::=
	SEQUENCE {
		psmStorageCyclicMaxFileCountLevelName DisplayString,
		psmStorageCyclicMaxFileCountLevelVal  CounterBasedGauge64,
		psmStorageCyclicMaxFileCountLevelMax  CounterBasedGauge64
	}

psmStorageCyclicMaxFileCountLevelName OBJECT-TYPE
	SYNTAX      DisplayString
	MAX-ACCESS  not-accessible
	STATUS      current
	DESCRIPTION
	"Max file count"
	::={ psmStorageCyclicMaxFileCountLevelEntry 1}

psmStorageCyclicMaxFileCountLevelVal OBJECT-TYPE
	SYNTAX     CounterBasedGauge64
	MAX-ACCESS read-only
	STATUS     current
	DESCRIPTION
	"Max file count"
	::={ psmStorageCyclicMaxFileCountLevelEntry 2 }

psmStorageCyclicMaxFileCountLevelMax OBJECT-TYPE
	SYNTAX     CounterBasedGauge64
	MAX-ACCESS read-only
	STATUS     current
	DESCRIPTION
	"Max file count"
	::={ psmStorageCyclicMaxFileCountLevelEntry 4 }

psmStorageCyclicMaxFileSize OBJECT IDENTIFIER ::= { psmStorageCyclic 6 }

psmStorageCyclicMaxFileSizeVal OBJECT-TYPE
	SYNTAX     CounterBasedGauge64
	MAX-ACCESS read-only
	STATUS     current
	DESCRIPTION "Max file size"

	::={ psmStorageCyclicMaxFileSize 1 }

psmStorageCyclicMaxFileSizeMax OBJECT-TYPE
	SYNTAX     CounterBasedGauge64
	MAX-ACCESS read-only
	STATUS     current
	DESCRIPTION "Max file size"

	::={ psmStorageCyclicMaxFileSize 3 }

psmStorageCyclicMaxFileSizeLevelTable OBJECT-TYPE
	SYNTAX     SEQUENCE OF PsmStorageCyclicMaxFileSizeLevelEntry
	MAX-ACCESS not-accessible
	STATUS     current
	DESCRIPTION
	"Max file size"
	::={ psmStorageCyclicMaxFileSize 4 }

psmStorageCyclicMaxFileSizeLevelEntry OBJECT-TYPE
	SYNTAX      PsmStorageCyclicMaxFileSizeLevelEntry
	MAX-ACCESS  not-accessible
	STATUS      current
	DESCRIPTION
	"Max file size"
	INDEX { psmStorageCyclicMaxFileSizeLevelName }
	::={ psmStorageCyclicMaxFileSizeLevelTable 1 }

PsmStorageCyclicMaxFileSizeLevelEntry ::=
	SEQUENCE {
		psmStorageCyclicMaxFileSizeLevelName DisplayString,
		psmStorageCyclicMaxFileSizeLevelVal  CounterBasedGauge64,
		psmStorageCyclicMaxFileSizeLevelMax  CounterBasedGauge64
	}

psmStorageCyclicMaxFileSizeLevelName OBJECT-TYPE
	SYNTAX      DisplayString
	MAX-ACCESS  not-accessible
	STATUS      current
	DESCRIPTION
	"Max file size"
	::={ psmStorageCyclicMaxFileSizeLevelEntry 1}

psmStorageCyclicMaxFileSizeLevelVal OBJECT-TYPE
	SYNTAX     CounterBasedGauge64
	MAX-ACCESS read-only
	STATUS     current
	DESCRIPTION
	"Max file size"
	::={ psmStorageCyclicMaxFileSizeLevelEntry 2 }

psmStorageCyclicMaxFileSizeLevelMax OBJECT-TYPE
	SYNTAX     CounterBasedGauge64
	MAX-ACCESS read-only
	STATUS     current
	DESCRIPTION
	"Max file size"
	::={ psmStorageCyclicMaxFileSizeLevelEntry 4 }

psmStorageCyclicObjectCountInModel OBJECT IDENTIFIER ::= { psmStorageCyclic 7 }

psmStorageCyclicObjectCountInModelVal OBJECT-TYPE
	SYNTAX     CounterBasedGauge64
	MAX-ACCESS read-only
	STATUS     current
	DESCRIPTION "Object count in model"

	::={ psmStorageCyclicObjectCountInModel 1 }

psmStorageCyclicObjectCountInModelMax OBJECT-TYPE
	SYNTAX     CounterBasedGauge64
	MAX-ACCESS read-only
	STATUS     current
	DESCRIPTION "Object count in model"

	::={ psmStorageCyclicObjectCountInModel 3 }

psmStorageCyclicObjectCountInModelLevelTable OBJECT-TYPE
	SYNTAX     SEQUENCE OF PsmStorageCyclicObjectCountInModelLevelEntry
	MAX-ACCESS not-accessible
	STATUS     current
	DESCRIPTION
	"Object count in model"
	::={ psmStorageCyclicObjectCountInModel 4 }

psmStorageCyclicObjectCountInModelLevelEntry OBJECT-TYPE
	SYNTAX      PsmStorageCyclicObjectCountInModelLevelEntry
	MAX-ACCESS  not-accessible
	STATUS      current
	DESCRIPTION
	"Object count in model"
	INDEX { psmStorageCyclicObjectCountInModelLevelName }
	::={ psmStorageCyclicObjectCountInModelLevelTable 1 }

PsmStorageCyclicObjectCountInModelLevelEntry ::=
	SEQUENCE {
		psmStorageCyclicObjectCountInModelLevelName DisplayString,
		psmStorageCyclicObjectCountInModelLevelVal  CounterBasedGauge64,
		psmStorageCyclicObjectCountInModelLevelMax  CounterBasedGauge64
	}

psmStorageCyclicObjectCountInModelLevelName OBJECT-TYPE
	SYNTAX      DisplayString
	MAX-ACCESS  not-accessible
	STATUS      current
	DESCRIPTION
	"Object count in model"
	::={ psmStorageCyclicObjectCountInModelLevelEntry 1}

psmStorageCyclicObjectCountInModelLevelVal OBJECT-TYPE
	SYNTAX     CounterBasedGauge64
	MAX-ACCESS read-only
	STATUS     current
	DESCRIPTION
	"Object count in model"
	::={ psmStorageCyclicObjectCountInModelLevelEntry 2 }

psmStorageCyclicObjectCountInModelLevelMax OBJECT-TYPE
	SYNTAX     CounterBasedGauge64
	MAX-ACCESS read-only
	STATUS     current
	DESCRIPTION
	"Object count in model"
	::={ psmStorageCyclicObjectCountInModelLevelEntry 4 }

psmStorageCyclicTotalRenewedObjectsWritten OBJECT IDENTIFIER ::= { psmStorageCyclic 8 }

psmStorageCyclicTotalRenewedObjectsWrittenVal OBJECT-TYPE
	SYNTAX     Counter64
	MAX-ACCESS read-only
	STATUS     current
	DESCRIPTION "Total renewed objects written"

	::={ psmStorageCyclicTotalRenewedObjectsWritten 1 }

psmStorageCyclicTotalRenewedObjectsWrittenMom OBJECT-TYPE
	SYNTAX     CounterBasedGauge64
	MAX-ACCESS read-only
	STATUS     current
	DESCRIPTION "Total renewed objects written"

	::={ psmStorageCyclicTotalRenewedObjectsWritten 2 }

psmStorageCyclicTotalRenewedObjectsWrittenMax OBJECT-TYPE
	SYNTAX     CounterBasedGauge64
	MAX-ACCESS read-only
	STATUS     current
	DESCRIPTION "Total renewed objects written"

	::={ psmStorageCyclicTotalRenewedObjectsWritten 3 }

psmStorageCyclicTotalRenewedObjectsWrittenLevelTable OBJECT-TYPE
	SYNTAX     SEQUENCE OF PsmStorageCyclicTotalRenewedObjectsWrittenLevelEntry
	MAX-ACCESS not-accessible
	STATUS     current
	DESCRIPTION
	"Total renewed objects written"
	::={ psmStorageCyclicTotalRenewedObjectsWritten 4 }

psmStorageCyclicTotalRenewedObjectsWrittenLevelEntry OBJECT-TYPE
	SYNTAX      PsmStorageCyclicTotalRenewedObjectsWrittenLevelEntry
	MAX-ACCESS  not-accessible
	STATUS      current
	DESCRIPTION
	"Total renewed objects written"
	INDEX { psmStorageCyclicTotalRenewedObjectsWrittenLevelName }
	::={ psmStorageCyclicTotalRenewedObjectsWrittenLevelTable 1 }

PsmStorageCyclicTotalRenewedObjectsWrittenLevelEntry ::=
	SEQUENCE {
		psmStorageCyclicTotalRenewedObjectsWrittenLevelName DisplayString,
		psmStorageCyclicTotalRenewedObjectsWrittenLevelVal  Counter64,
		psmStorageCyclicTotalRenewedObjectsWrittenLevelMom  CounterBasedGauge64,
		psmStorageCyclicTotalRenewedObjectsWrittenLevelMax  CounterBasedGauge64
	}

psmStorageCyclicTotalRenewedObjectsWrittenLevelName OBJECT-TYPE
	SYNTAX      DisplayString
	MAX-ACCESS  not-accessible
	STATUS      current
	DESCRIPTION
	"Total renewed objects written"
	::={ psmStorageCyclicTotalRenewedObjectsWrittenLevelEntry 1}

psmStorageCyclicTotalRenewedObjectsWrittenLevelVal OBJECT-TYPE
	SYNTAX     Counter64
	MAX-ACCESS read-only
	STATUS     current
	DESCRIPTION
	"Total renewed objects written"
	::={ psmStorageCyclicTotalRenewedObjectsWrittenLevelEntry 2 }

psmStorageCyclicTotalRenewedObjectsWrittenLevelMom OBJECT-TYPE
	SYNTAX     CounterBasedGauge64
	MAX-ACCESS read-only
	STATUS     current
	DESCRIPTION
	"Total renewed objects written"
	::={ psmStorageCyclicTotalRenewedObjectsWrittenLevelEntry 3 }

psmStorageCyclicTotalRenewedObjectsWrittenLevelMax OBJECT-TYPE
	SYNTAX     CounterBasedGauge64
	MAX-ACCESS read-only
	STATUS     current
	DESCRIPTION
	"Total renewed objects written"
	::={ psmStorageCyclicTotalRenewedObjectsWrittenLevelEntry 4 }

psmStorageCyclicState OBJECT IDENTIFIER ::= { psmStorageCyclic 9 }

psmStorageCyclicStateVal OBJECT-TYPE
	SYNTAX     INTEGER {
		stopped(0),
		synchronizing(1),
		loading(2),
		insync(3)
	}
	MAX-ACCESS read-only
	STATUS     current
	DESCRIPTION "State"

	::={ psmStorageCyclicState 1 }

psmStorageCyclicStateLevelTable OBJECT-TYPE
	SYNTAX     SEQUENCE OF PsmStorageCyclicStateLevelEntry
	MAX-ACCESS not-accessible
	STATUS     current
	DESCRIPTION
	"State"
	::={ psmStorageCyclicState 4 }

psmStorageCyclicStateLevelEntry OBJECT-TYPE
	SYNTAX      PsmStorageCyclicStateLevelEntry
	MAX-ACCESS  not-accessible
	STATUS      current
	DESCRIPTION
	"State"
	INDEX { psmStorageCyclicStateLevelName }
	::={ psmStorageCyclicStateLevelTable 1 }

PsmStorageCyclicStateLevelEntry ::=
	SEQUENCE {
		psmStorageCyclicStateLevelName DisplayString,
		psmStorageCyclicStateLevelVal  INTEGER
	}

psmStorageCyclicStateLevelName OBJECT-TYPE
	SYNTAX      DisplayString
	MAX-ACCESS  not-accessible
	STATUS      current
	DESCRIPTION
	"State"
	::={ psmStorageCyclicStateLevelEntry 1}

psmStorageCyclicStateLevelVal OBJECT-TYPE
	SYNTAX     INTEGER {
		stopped(0),
		synchronizing(1),
		loading(2),
		insync(3)
	}
	MAX-ACCESS read-only
	STATUS     current
	DESCRIPTION
	"State"
	::={ psmStorageCyclicStateLevelEntry 2 }

psmStorageCyclicUsedFileCount OBJECT IDENTIFIER ::= { psmStorageCyclic 10 }

psmStorageCyclicUsedFileCountVal OBJECT-TYPE
	SYNTAX     CounterBasedGauge64
	MAX-ACCESS read-only
	STATUS     current
	DESCRIPTION "Used file count"

	::={ psmStorageCyclicUsedFileCount 1 }

psmStorageCyclicUsedFileCountMax OBJECT-TYPE
	SYNTAX     CounterBasedGauge64
	MAX-ACCESS read-only
	STATUS     current
	DESCRIPTION "Used file count"

	::={ psmStorageCyclicUsedFileCount 3 }

psmStorageCyclicUsedFileCountLevelTable OBJECT-TYPE
	SYNTAX     SEQUENCE OF PsmStorageCyclicUsedFileCountLevelEntry
	MAX-ACCESS not-accessible
	STATUS     current
	DESCRIPTION
	"Used file count"
	::={ psmStorageCyclicUsedFileCount 4 }

psmStorageCyclicUsedFileCountLevelEntry OBJECT-TYPE
	SYNTAX      PsmStorageCyclicUsedFileCountLevelEntry
	MAX-ACCESS  not-accessible
	STATUS      current
	DESCRIPTION
	"Used file count"
	INDEX { psmStorageCyclicUsedFileCountLevelName }
	::={ psmStorageCyclicUsedFileCountLevelTable 1 }

PsmStorageCyclicUsedFileCountLevelEntry ::=
	SEQUENCE {
		psmStorageCyclicUsedFileCountLevelName DisplayString,
		psmStorageCyclicUsedFileCountLevelVal  CounterBasedGauge64,
		psmStorageCyclicUsedFileCountLevelMax  CounterBasedGauge64
	}

psmStorageCyclicUsedFileCountLevelName OBJECT-TYPE
	SYNTAX      DisplayString
	MAX-ACCESS  not-accessible
	STATUS      current
	DESCRIPTION
	"Used file count"
	::={ psmStorageCyclicUsedFileCountLevelEntry 1}

psmStorageCyclicUsedFileCountLevelVal OBJECT-TYPE
	SYNTAX     CounterBasedGauge64
	MAX-ACCESS read-only
	STATUS     current
	DESCRIPTION
	"Used file count"
	::={ psmStorageCyclicUsedFileCountLevelEntry 2 }

psmStorageCyclicUsedFileCountLevelMax OBJECT-TYPE
	SYNTAX     CounterBasedGauge64
	MAX-ACCESS read-only
	STATUS     current
	DESCRIPTION
	"Used file count"
	::={ psmStorageCyclicUsedFileCountLevelEntry 4 }

psmSourceTCP OBJECT IDENTIFIER ::= { psmv2 5 }

psmSourceTCPConnections OBJECT IDENTIFIER ::= { psmSourceTCP 1 }

psmSourceTCPConnectionsVal OBJECT-TYPE
	SYNTAX     Counter64
	MAX-ACCESS read-only
	STATUS     current
	DESCRIPTION "Connections"

	::={ psmSourceTCPConnections 1 }

psmSourceTCPConnectionsMom OBJECT-TYPE
	SYNTAX     CounterBasedGauge64
	MAX-ACCESS read-only
	STATUS     current
	DESCRIPTION "Connections"

	::={ psmSourceTCPConnections 2 }

psmSourceTCPConnectionsMax OBJECT-TYPE
	SYNTAX     CounterBasedGauge64
	MAX-ACCESS read-only
	STATUS     current
	DESCRIPTION "Connections"

	::={ psmSourceTCPConnections 3 }

psmSourceTCPConnectionsLevelTable OBJECT-TYPE
	SYNTAX     SEQUENCE OF PsmSourceTCPConnectionsLevelEntry
	MAX-ACCESS not-accessible
	STATUS     current
	DESCRIPTION
	"Connections"
	::={ psmSourceTCPConnections 4 }

psmSourceTCPConnectionsLevelEntry OBJECT-TYPE
	SYNTAX      PsmSourceTCPConnectionsLevelEntry
	MAX-ACCESS  not-accessible
	STATUS      current
	DESCRIPTION
	"Connections"
	INDEX { psmSourceTCPConnectionsLevelName }
	::={ psmSourceTCPConnectionsLevelTable 1 }

PsmSourceTCPConnectionsLevelEntry ::=
	SEQUENCE {
		psmSourceTCPConnectionsLevelName DisplayString,
		psmSourceTCPConnectionsLevelVal  Counter64,
		psmSourceTCPConnectionsLevelMom  CounterBasedGauge64,
		psmSourceTCPConnectionsLevelMax  CounterBasedGauge64
	}

psmSourceTCPConnectionsLevelName OBJECT-TYPE
	SYNTAX      DisplayString
	MAX-ACCESS  not-accessible
	STATUS      current
	DESCRIPTION
	"Connections"
	::={ psmSourceTCPConnectionsLevelEntry 1}

psmSourceTCPConnectionsLevelVal OBJECT-TYPE
	SYNTAX     Counter64
	MAX-ACCESS read-only
	STATUS     current
	DESCRIPTION
	"Connections"
	::={ psmSourceTCPConnectionsLevelEntry 2 }

psmSourceTCPConnectionsLevelMom OBJECT-TYPE
	SYNTAX     CounterBasedGauge64
	MAX-ACCESS read-only
	STATUS     current
	DESCRIPTION
	"Connections"
	::={ psmSourceTCPConnectionsLevelEntry 3 }

psmSourceTCPConnectionsLevelMax OBJECT-TYPE
	SYNTAX     CounterBasedGauge64
	MAX-ACCESS read-only
	STATUS     current
	DESCRIPTION
	"Connections"
	::={ psmSourceTCPConnectionsLevelEntry 4 }

psmSourceTCPFailures OBJECT IDENTIFIER ::= { psmSourceTCP 2 }

psmSourceTCPFailuresVal OBJECT-TYPE
	SYNTAX     Counter64
	MAX-ACCESS read-only
	STATUS     current
	DESCRIPTION "Failures"

	::={ psmSourceTCPFailures 1 }

psmSourceTCPFailuresMom OBJECT-TYPE
	SYNTAX     CounterBasedGauge64
	MAX-ACCESS read-only
	STATUS     current
	DESCRIPTION "Failures"

	::={ psmSourceTCPFailures 2 }

psmSourceTCPFailuresMax OBJECT-TYPE
	SYNTAX     CounterBasedGauge64
	MAX-ACCESS read-only
	STATUS     current
	DESCRIPTION "Failures"

	::={ psmSourceTCPFailures 3 }

psmSourceTCPFailuresLevelTable OBJECT-TYPE
	SYNTAX     SEQUENCE OF PsmSourceTCPFailuresLevelEntry
	MAX-ACCESS not-accessible
	STATUS     current
	DESCRIPTION
	"Failures"
	::={ psmSourceTCPFailures 4 }

psmSourceTCPFailuresLevelEntry OBJECT-TYPE
	SYNTAX      PsmSourceTCPFailuresLevelEntry
	MAX-ACCESS  not-accessible
	STATUS      current
	DESCRIPTION
	"Failures"
	INDEX { psmSourceTCPFailuresLevelName }
	::={ psmSourceTCPFailuresLevelTable 1 }

PsmSourceTCPFailuresLevelEntry ::=
	SEQUENCE {
		psmSourceTCPFailuresLevelName DisplayString,
		psmSourceTCPFailuresLevelVal  Counter64,
		psmSourceTCPFailuresLevelMom  CounterBasedGauge64,
		psmSourceTCPFailuresLevelMax  CounterBasedGauge64
	}

psmSourceTCPFailuresLevelName OBJECT-TYPE
	SYNTAX      DisplayString
	MAX-ACCESS  not-accessible
	STATUS      current
	DESCRIPTION
	"Failures"
	::={ psmSourceTCPFailuresLevelEntry 1}

psmSourceTCPFailuresLevelVal OBJECT-TYPE
	SYNTAX     Counter64
	MAX-ACCESS read-only
	STATUS     current
	DESCRIPTION
	"Failures"
	::={ psmSourceTCPFailuresLevelEntry 2 }

psmSourceTCPFailuresLevelMom OBJECT-TYPE
	SYNTAX     CounterBasedGauge64
	MAX-ACCESS read-only
	STATUS     current
	DESCRIPTION
	"Failures"
	::={ psmSourceTCPFailuresLevelEntry 3 }

psmSourceTCPFailuresLevelMax OBJECT-TYPE
	SYNTAX     CounterBasedGauge64
	MAX-ACCESS read-only
	STATUS     current
	DESCRIPTION
	"Failures"
	::={ psmSourceTCPFailuresLevelEntry 4 }

psmSourceTCPRejects OBJECT IDENTIFIER ::= { psmSourceTCP 3 }

psmSourceTCPRejectsVal OBJECT-TYPE
	SYNTAX     Counter64
	MAX-ACCESS read-only
	STATUS     current
	DESCRIPTION "Rejects"

	::={ psmSourceTCPRejects 1 }

psmSourceTCPRejectsMom OBJECT-TYPE
	SYNTAX     CounterBasedGauge64
	MAX-ACCESS read-only
	STATUS     current
	DESCRIPTION "Rejects"

	::={ psmSourceTCPRejects 2 }

psmSourceTCPRejectsMax OBJECT-TYPE
	SYNTAX     CounterBasedGauge64
	MAX-ACCESS read-only
	STATUS     current
	DESCRIPTION "Rejects"

	::={ psmSourceTCPRejects 3 }

psmSourceTCPRejectsLevelTable OBJECT-TYPE
	SYNTAX     SEQUENCE OF PsmSourceTCPRejectsLevelEntry
	MAX-ACCESS not-accessible
	STATUS     current
	DESCRIPTION
	"Rejects"
	::={ psmSourceTCPRejects 4 }

psmSourceTCPRejectsLevelEntry OBJECT-TYPE
	SYNTAX      PsmSourceTCPRejectsLevelEntry
	MAX-ACCESS  not-accessible
	STATUS      current
	DESCRIPTION
	"Rejects"
	INDEX { psmSourceTCPRejectsLevelName }
	::={ psmSourceTCPRejectsLevelTable 1 }

PsmSourceTCPRejectsLevelEntry ::=
	SEQUENCE {
		psmSourceTCPRejectsLevelName DisplayString,
		psmSourceTCPRejectsLevelVal  Counter64,
		psmSourceTCPRejectsLevelMom  CounterBasedGauge64,
		psmSourceTCPRejectsLevelMax  CounterBasedGauge64
	}

psmSourceTCPRejectsLevelName OBJECT-TYPE
	SYNTAX      DisplayString
	MAX-ACCESS  not-accessible
	STATUS      current
	DESCRIPTION
	"Rejects"
	::={ psmSourceTCPRejectsLevelEntry 1}

psmSourceTCPRejectsLevelVal OBJECT-TYPE
	SYNTAX     Counter64
	MAX-ACCESS read-only
	STATUS     current
	DESCRIPTION
	"Rejects"
	::={ psmSourceTCPRejectsLevelEntry 2 }

psmSourceTCPRejectsLevelMom OBJECT-TYPE
	SYNTAX     CounterBasedGauge64
	MAX-ACCESS read-only
	STATUS     current
	DESCRIPTION
	"Rejects"
	::={ psmSourceTCPRejectsLevelEntry 3 }

psmSourceTCPRejectsLevelMax OBJECT-TYPE
	SYNTAX     CounterBasedGauge64
	MAX-ACCESS read-only
	STATUS     current
	DESCRIPTION
	"Rejects"
	::={ psmSourceTCPRejectsLevelEntry 4 }

psmSourceTCPRequests OBJECT IDENTIFIER ::= { psmSourceTCP 4 }

psmSourceTCPRequestsVal OBJECT-TYPE
	SYNTAX     Counter64
	MAX-ACCESS read-only
	STATUS     current
	DESCRIPTION "Requests"

	::={ psmSourceTCPRequests 1 }

psmSourceTCPRequestsMom OBJECT-TYPE
	SYNTAX     CounterBasedGauge64
	MAX-ACCESS read-only
	STATUS     current
	DESCRIPTION "Requests"

	::={ psmSourceTCPRequests 2 }

psmSourceTCPRequestsMax OBJECT-TYPE
	SYNTAX     CounterBasedGauge64
	MAX-ACCESS read-only
	STATUS     current
	DESCRIPTION "Requests"

	::={ psmSourceTCPRequests 3 }

psmSourceTCPRequestsLevelTable OBJECT-TYPE
	SYNTAX     SEQUENCE OF PsmSourceTCPRequestsLevelEntry
	MAX-ACCESS not-accessible
	STATUS     current
	DESCRIPTION
	"Requests"
	::={ psmSourceTCPRequests 4 }

psmSourceTCPRequestsLevelEntry OBJECT-TYPE
	SYNTAX      PsmSourceTCPRequestsLevelEntry
	MAX-ACCESS  not-accessible
	STATUS      current
	DESCRIPTION
	"Requests"
	INDEX { psmSourceTCPRequestsLevelName }
	::={ psmSourceTCPRequestsLevelTable 1 }

PsmSourceTCPRequestsLevelEntry ::=
	SEQUENCE {
		psmSourceTCPRequestsLevelName DisplayString,
		psmSourceTCPRequestsLevelVal  Counter64,
		psmSourceTCPRequestsLevelMom  CounterBasedGauge64,
		psmSourceTCPRequestsLevelMax  CounterBasedGauge64
	}

psmSourceTCPRequestsLevelName OBJECT-TYPE
	SYNTAX      DisplayString
	MAX-ACCESS  not-accessible
	STATUS      current
	DESCRIPTION
	"Requests"
	::={ psmSourceTCPRequestsLevelEntry 1}

psmSourceTCPRequestsLevelVal OBJECT-TYPE
	SYNTAX     Counter64
	MAX-ACCESS read-only
	STATUS     current
	DESCRIPTION
	"Requests"
	::={ psmSourceTCPRequestsLevelEntry 2 }

psmSourceTCPRequestsLevelMom OBJECT-TYPE
	SYNTAX     CounterBasedGauge64
	MAX-ACCESS read-only
	STATUS     current
	DESCRIPTION
	"Requests"
	::={ psmSourceTCPRequestsLevelEntry 3 }

psmSourceTCPRequestsLevelMax OBJECT-TYPE
	SYNTAX     CounterBasedGauge64
	MAX-ACCESS read-only
	STATUS     current
	DESCRIPTION
	"Requests"
	::={ psmSourceTCPRequestsLevelEntry 4 }

psmSourceTCPTotalConnections OBJECT IDENTIFIER ::= { psmSourceTCP 5 }

psmSourceTCPTotalConnectionsVal OBJECT-TYPE
	SYNTAX     CounterBasedGauge64
	MAX-ACCESS read-only
	STATUS     current
	DESCRIPTION "Total connections"

	::={ psmSourceTCPTotalConnections 1 }

psmSourceTCPTotalConnectionsMax OBJECT-TYPE
	SYNTAX     CounterBasedGauge64
	MAX-ACCESS read-only
	STATUS     current
	DESCRIPTION "Total connections"

	::={ psmSourceTCPTotalConnections 3 }

psmSourceTCPTotalConnectionsLevelTable OBJECT-TYPE
	SYNTAX     SEQUENCE OF PsmSourceTCPTotalConnectionsLevelEntry
	MAX-ACCESS not-accessible
	STATUS     current
	DESCRIPTION
	"Total connections"
	::={ psmSourceTCPTotalConnections 4 }

psmSourceTCPTotalConnectionsLevelEntry OBJECT-TYPE
	SYNTAX      PsmSourceTCPTotalConnectionsLevelEntry
	MAX-ACCESS  not-accessible
	STATUS      current
	DESCRIPTION
	"Total connections"
	INDEX { psmSourceTCPTotalConnectionsLevelName }
	::={ psmSourceTCPTotalConnectionsLevelTable 1 }

PsmSourceTCPTotalConnectionsLevelEntry ::=
	SEQUENCE {
		psmSourceTCPTotalConnectionsLevelName DisplayString,
		psmSourceTCPTotalConnectionsLevelVal  CounterBasedGauge64,
		psmSourceTCPTotalConnectionsLevelMax  CounterBasedGauge64
	}

psmSourceTCPTotalConnectionsLevelName OBJECT-TYPE
	SYNTAX      DisplayString
	MAX-ACCESS  not-accessible
	STATUS      current
	DESCRIPTION
	"Total connections"
	::={ psmSourceTCPTotalConnectionsLevelEntry 1}

psmSourceTCPTotalConnectionsLevelVal OBJECT-TYPE
	SYNTAX     CounterBasedGauge64
	MAX-ACCESS read-only
	STATUS     current
	DESCRIPTION
	"Total connections"
	::={ psmSourceTCPTotalConnectionsLevelEntry 2 }

psmSourceTCPTotalConnectionsLevelMax OBJECT-TYPE
	SYNTAX     CounterBasedGauge64
	MAX-ACCESS read-only
	STATUS     current
	DESCRIPTION
	"Total connections"
	::={ psmSourceTCPTotalConnectionsLevelEntry 4 }

psmSourceSOAP OBJECT IDENTIFIER ::= { psmv2 11 }

psmSourceSOAPFailures OBJECT IDENTIFIER ::= { psmSourceSOAP 1 }

psmSourceSOAPFailuresVal OBJECT-TYPE
	SYNTAX     Counter64
	MAX-ACCESS read-only
	STATUS     current
	DESCRIPTION "Failures"

	::={ psmSourceSOAPFailures 1 }

psmSourceSOAPFailuresMom OBJECT-TYPE
	SYNTAX     CounterBasedGauge64
	MAX-ACCESS read-only
	STATUS     current
	DESCRIPTION "Failures"

	::={ psmSourceSOAPFailures 2 }

psmSourceSOAPFailuresMax OBJECT-TYPE
	SYNTAX     CounterBasedGauge64
	MAX-ACCESS read-only
	STATUS     current
	DESCRIPTION "Failures"

	::={ psmSourceSOAPFailures 3 }

psmSourceSOAPFailuresLevelTable OBJECT-TYPE
	SYNTAX     SEQUENCE OF PsmSourceSOAPFailuresLevelEntry
	MAX-ACCESS not-accessible
	STATUS     current
	DESCRIPTION
	"Failures"
	::={ psmSourceSOAPFailures 4 }

psmSourceSOAPFailuresLevelEntry OBJECT-TYPE
	SYNTAX      PsmSourceSOAPFailuresLevelEntry
	MAX-ACCESS  not-accessible
	STATUS      current
	DESCRIPTION
	"Failures"
	INDEX { psmSourceSOAPFailuresLevelName }
	::={ psmSourceSOAPFailuresLevelTable 1 }

PsmSourceSOAPFailuresLevelEntry ::=
	SEQUENCE {
		psmSourceSOAPFailuresLevelName DisplayString,
		psmSourceSOAPFailuresLevelVal  Counter64,
		psmSourceSOAPFailuresLevelMom  CounterBasedGauge64,
		psmSourceSOAPFailuresLevelMax  CounterBasedGauge64
	}

psmSourceSOAPFailuresLevelName OBJECT-TYPE
	SYNTAX      DisplayString
	MAX-ACCESS  not-accessible
	STATUS      current
	DESCRIPTION
	"Failures"
	::={ psmSourceSOAPFailuresLevelEntry 1}

psmSourceSOAPFailuresLevelVal OBJECT-TYPE
	SYNTAX     Counter64
	MAX-ACCESS read-only
	STATUS     current
	DESCRIPTION
	"Failures"
	::={ psmSourceSOAPFailuresLevelEntry 2 }

psmSourceSOAPFailuresLevelMom OBJECT-TYPE
	SYNTAX     CounterBasedGauge64
	MAX-ACCESS read-only
	STATUS     current
	DESCRIPTION
	"Failures"
	::={ psmSourceSOAPFailuresLevelEntry 3 }

psmSourceSOAPFailuresLevelMax OBJECT-TYPE
	SYNTAX     CounterBasedGauge64
	MAX-ACCESS read-only
	STATUS     current
	DESCRIPTION
	"Failures"
	::={ psmSourceSOAPFailuresLevelEntry 4 }

psmSourceSOAPRequests OBJECT IDENTIFIER ::= { psmSourceSOAP 2 }

psmSourceSOAPRequestsVal OBJECT-TYPE
	SYNTAX     Counter64
	MAX-ACCESS read-only
	STATUS     current
	DESCRIPTION "Requests"

	::={ psmSourceSOAPRequests 1 }

psmSourceSOAPRequestsMom OBJECT-TYPE
	SYNTAX     CounterBasedGauge64
	MAX-ACCESS read-only
	STATUS     current
	DESCRIPTION "Requests"

	::={ psmSourceSOAPRequests 2 }

psmSourceSOAPRequestsMax OBJECT-TYPE
	SYNTAX     CounterBasedGauge64
	MAX-ACCESS read-only
	STATUS     current
	DESCRIPTION "Requests"

	::={ psmSourceSOAPRequests 3 }

psmSourceSOAPRequestsLevelTable OBJECT-TYPE
	SYNTAX     SEQUENCE OF PsmSourceSOAPRequestsLevelEntry
	MAX-ACCESS not-accessible
	STATUS     current
	DESCRIPTION
	"Requests"
	::={ psmSourceSOAPRequests 4 }

psmSourceSOAPRequestsLevelEntry OBJECT-TYPE
	SYNTAX      PsmSourceSOAPRequestsLevelEntry
	MAX-ACCESS  not-accessible
	STATUS      current
	DESCRIPTION
	"Requests"
	INDEX { psmSourceSOAPRequestsLevelName }
	::={ psmSourceSOAPRequestsLevelTable 1 }

PsmSourceSOAPRequestsLevelEntry ::=
	SEQUENCE {
		psmSourceSOAPRequestsLevelName DisplayString,
		psmSourceSOAPRequestsLevelVal  Counter64,
		psmSourceSOAPRequestsLevelMom  CounterBasedGauge64,
		psmSourceSOAPRequestsLevelMax  CounterBasedGauge64
	}

psmSourceSOAPRequestsLevelName OBJECT-TYPE
	SYNTAX      DisplayString
	MAX-ACCESS  not-accessible
	STATUS      current
	DESCRIPTION
	"Requests"
	::={ psmSourceSOAPRequestsLevelEntry 1}

psmSourceSOAPRequestsLevelVal OBJECT-TYPE
	SYNTAX     Counter64
	MAX-ACCESS read-only
	STATUS     current
	DESCRIPTION
	"Requests"
	::={ psmSourceSOAPRequestsLevelEntry 2 }

psmSourceSOAPRequestsLevelMom OBJECT-TYPE
	SYNTAX     CounterBasedGauge64
	MAX-ACCESS read-only
	STATUS     current
	DESCRIPTION
	"Requests"
	::={ psmSourceSOAPRequestsLevelEntry 3 }

psmSourceSOAPRequestsLevelMax OBJECT-TYPE
	SYNTAX     CounterBasedGauge64
	MAX-ACCESS read-only
	STATUS     current
	DESCRIPTION
	"Requests"
	::={ psmSourceSOAPRequestsLevelEntry 4 }

psmRedundancy OBJECT IDENTIFIER ::= { psmv2 2 }

psmRedundancyRedundancyStateChanged OBJECT IDENTIFIER ::= { psmRedundancy 1 }

psmRedundancyRedundancyStateChangedVal OBJECT-TYPE
	SYNTAX     DateAndTime
	MAX-ACCESS read-only
	STATUS     current
	DESCRIPTION "Redundancy state changed"

	::={ psmRedundancyRedundancyStateChanged 1 }

psmRedundancyRedundancyStateChangedLevelTable OBJECT-TYPE
	SYNTAX     SEQUENCE OF PsmRedundancyRedundancyStateChangedLevelEntry
	MAX-ACCESS not-accessible
	STATUS     current
	DESCRIPTION
	"Redundancy state changed"
	::={ psmRedundancyRedundancyStateChanged 4 }

psmRedundancyRedundancyStateChangedLevelEntry OBJECT-TYPE
	SYNTAX      PsmRedundancyRedundancyStateChangedLevelEntry
	MAX-ACCESS  not-accessible
	STATUS      current
	DESCRIPTION
	"Redundancy state changed"
	INDEX { psmRedundancyRedundancyStateChangedLevelName }
	::={ psmRedundancyRedundancyStateChangedLevelTable 1 }

PsmRedundancyRedundancyStateChangedLevelEntry ::=
	SEQUENCE {
		psmRedundancyRedundancyStateChangedLevelName DisplayString,
		psmRedundancyRedundancyStateChangedLevelVal  DateAndTime
	}

psmRedundancyRedundancyStateChangedLevelName OBJECT-TYPE
	SYNTAX      DisplayString
	MAX-ACCESS  not-accessible
	STATUS      current
	DESCRIPTION
	"Redundancy state changed"
	::={ psmRedundancyRedundancyStateChangedLevelEntry 1}

psmRedundancyRedundancyStateChangedLevelVal OBJECT-TYPE
	SYNTAX     DateAndTime
	MAX-ACCESS read-only
	STATUS     current
	DESCRIPTION
	"Redundancy state changed"
	::={ psmRedundancyRedundancyStateChangedLevelEntry 2 }

psmRedundancyRedundancyState OBJECT IDENTIFIER ::= { psmRedundancy 2 }

psmRedundancyRedundancyStateVal OBJECT-TYPE
	SYNTAX     INTEGER {
		offline(0),
		slave(1),
		master(2)
	}
	MAX-ACCESS read-only
	STATUS     current
	DESCRIPTION "Redundancy state"

	::={ psmRedundancyRedundancyState 1 }

psmRedundancyRedundancyStateLevelTable OBJECT-TYPE
	SYNTAX     SEQUENCE OF PsmRedundancyRedundancyStateLevelEntry
	MAX-ACCESS not-accessible
	STATUS     current
	DESCRIPTION
	"Redundancy state"
	::={ psmRedundancyRedundancyState 4 }

psmRedundancyRedundancyStateLevelEntry OBJECT-TYPE
	SYNTAX      PsmRedundancyRedundancyStateLevelEntry
	MAX-ACCESS  not-accessible
	STATUS      current
	DESCRIPTION
	"Redundancy state"
	INDEX { psmRedundancyRedundancyStateLevelName }
	::={ psmRedundancyRedundancyStateLevelTable 1 }

PsmRedundancyRedundancyStateLevelEntry ::=
	SEQUENCE {
		psmRedundancyRedundancyStateLevelName DisplayString,
		psmRedundancyRedundancyStateLevelVal  INTEGER
	}

psmRedundancyRedundancyStateLevelName OBJECT-TYPE
	SYNTAX      DisplayString
	MAX-ACCESS  not-accessible
	STATUS      current
	DESCRIPTION
	"Redundancy state"
	::={ psmRedundancyRedundancyStateLevelEntry 1}

psmRedundancyRedundancyStateLevelVal OBJECT-TYPE
	SYNTAX     INTEGER {
		offline(0),
		slave(1),
		master(2)
	}
	MAX-ACCESS read-only
	STATUS     current
	DESCRIPTION
	"Redundancy state"
	::={ psmRedundancyRedundancyStateLevelEntry 2 }

psmMisc OBJECT IDENTIFIER ::= { psmv2 7 }

psmMiscLostMessages OBJECT IDENTIFIER ::= { psmMisc 1 }

psmMiscLostMessagesVal OBJECT-TYPE
	SYNTAX     Counter64
	MAX-ACCESS read-only
	STATUS     current
	DESCRIPTION "Lost messages"

	::={ psmMiscLostMessages 1 }

psmMiscLostMessagesMom OBJECT-TYPE
	SYNTAX     CounterBasedGauge64
	MAX-ACCESS read-only
	STATUS     current
	DESCRIPTION "Lost messages"

	::={ psmMiscLostMessages 2 }

psmMiscLostMessagesMax OBJECT-TYPE
	SYNTAX     CounterBasedGauge64
	MAX-ACCESS read-only
	STATUS     current
	DESCRIPTION "Lost messages"

	::={ psmMiscLostMessages 3 }

psmMiscLostMessagesLevelTable OBJECT-TYPE
	SYNTAX     SEQUENCE OF PsmMiscLostMessagesLevelEntry
	MAX-ACCESS not-accessible
	STATUS     current
	DESCRIPTION
	"Lost messages"
	::={ psmMiscLostMessages 4 }

psmMiscLostMessagesLevelEntry OBJECT-TYPE
	SYNTAX      PsmMiscLostMessagesLevelEntry
	MAX-ACCESS  not-accessible
	STATUS      current
	DESCRIPTION
	"Lost messages"
	INDEX { psmMiscLostMessagesLevelName }
	::={ psmMiscLostMessagesLevelTable 1 }

PsmMiscLostMessagesLevelEntry ::=
	SEQUENCE {
		psmMiscLostMessagesLevelName DisplayString,
		psmMiscLostMessagesLevelVal  Counter64,
		psmMiscLostMessagesLevelMom  CounterBasedGauge64,
		psmMiscLostMessagesLevelMax  CounterBasedGauge64
	}

psmMiscLostMessagesLevelName OBJECT-TYPE
	SYNTAX      DisplayString
	MAX-ACCESS  not-accessible
	STATUS      current
	DESCRIPTION
	"Lost messages"
	::={ psmMiscLostMessagesLevelEntry 1}

psmMiscLostMessagesLevelVal OBJECT-TYPE
	SYNTAX     Counter64
	MAX-ACCESS read-only
	STATUS     current
	DESCRIPTION
	"Lost messages"
	::={ psmMiscLostMessagesLevelEntry 2 }

psmMiscLostMessagesLevelMom OBJECT-TYPE
	SYNTAX     CounterBasedGauge64
	MAX-ACCESS read-only
	STATUS     current
	DESCRIPTION
	"Lost messages"
	::={ psmMiscLostMessagesLevelEntry 3 }

psmMiscLostMessagesLevelMax OBJECT-TYPE
	SYNTAX     CounterBasedGauge64
	MAX-ACCESS read-only
	STATUS     current
	DESCRIPTION
	"Lost messages"
	::={ psmMiscLostMessagesLevelEntry 4 }

psmMiscWrittenMessages OBJECT IDENTIFIER ::= { psmMisc 2 }

psmMiscWrittenMessagesVal OBJECT-TYPE
	SYNTAX     Counter64
	MAX-ACCESS read-only
	STATUS     current
	DESCRIPTION "Written messages"

	::={ psmMiscWrittenMessages 1 }

psmMiscWrittenMessagesMom OBJECT-TYPE
	SYNTAX     CounterBasedGauge64
	MAX-ACCESS read-only
	STATUS     current
	DESCRIPTION "Written messages"

	::={ psmMiscWrittenMessages 2 }

psmMiscWrittenMessagesMax OBJECT-TYPE
	SYNTAX     CounterBasedGauge64
	MAX-ACCESS read-only
	STATUS     current
	DESCRIPTION "Written messages"

	::={ psmMiscWrittenMessages 3 }

psmMiscWrittenMessagesLevelTable OBJECT-TYPE
	SYNTAX     SEQUENCE OF PsmMiscWrittenMessagesLevelEntry
	MAX-ACCESS not-accessible
	STATUS     current
	DESCRIPTION
	"Written messages"
	::={ psmMiscWrittenMessages 4 }

psmMiscWrittenMessagesLevelEntry OBJECT-TYPE
	SYNTAX      PsmMiscWrittenMessagesLevelEntry
	MAX-ACCESS  not-accessible
	STATUS      current
	DESCRIPTION
	"Written messages"
	INDEX { psmMiscWrittenMessagesLevelName }
	::={ psmMiscWrittenMessagesLevelTable 1 }

PsmMiscWrittenMessagesLevelEntry ::=
	SEQUENCE {
		psmMiscWrittenMessagesLevelName DisplayString,
		psmMiscWrittenMessagesLevelVal  Counter64,
		psmMiscWrittenMessagesLevelMom  CounterBasedGauge64,
		psmMiscWrittenMessagesLevelMax  CounterBasedGauge64
	}

psmMiscWrittenMessagesLevelName OBJECT-TYPE
	SYNTAX      DisplayString
	MAX-ACCESS  not-accessible
	STATUS      current
	DESCRIPTION
	"Written messages"
	::={ psmMiscWrittenMessagesLevelEntry 1}

psmMiscWrittenMessagesLevelVal OBJECT-TYPE
	SYNTAX     Counter64
	MAX-ACCESS read-only
	STATUS     current
	DESCRIPTION
	"Written messages"
	::={ psmMiscWrittenMessagesLevelEntry 2 }

psmMiscWrittenMessagesLevelMom OBJECT-TYPE
	SYNTAX     CounterBasedGauge64
	MAX-ACCESS read-only
	STATUS     current
	DESCRIPTION
	"Written messages"
	::={ psmMiscWrittenMessagesLevelEntry 3 }

psmMiscWrittenMessagesLevelMax OBJECT-TYPE
	SYNTAX     CounterBasedGauge64
	MAX-ACCESS read-only
	STATUS     current
	DESCRIPTION
	"Written messages"
	::={ psmMiscWrittenMessagesLevelEntry 4 }

psmMiscDiameterRunning OBJECT IDENTIFIER ::= { psmMisc 3 }

psmMiscDiameterRunningVal OBJECT-TYPE
	SYNTAX     INTEGER {
		false(0),
		true(1)
	}
	MAX-ACCESS read-only
	STATUS     current
	DESCRIPTION "Diameter running"

	::={ psmMiscDiameterRunning 1 }

psmMiscDiameterRunningLevelTable OBJECT-TYPE
	SYNTAX     SEQUENCE OF PsmMiscDiameterRunningLevelEntry
	MAX-ACCESS not-accessible
	STATUS     current
	DESCRIPTION
	"Diameter running"
	::={ psmMiscDiameterRunning 4 }

psmMiscDiameterRunningLevelEntry OBJECT-TYPE
	SYNTAX      PsmMiscDiameterRunningLevelEntry
	MAX-ACCESS  not-accessible
	STATUS      current
	DESCRIPTION
	"Diameter running"
	INDEX { psmMiscDiameterRunningLevelName }
	::={ psmMiscDiameterRunningLevelTable 1 }

PsmMiscDiameterRunningLevelEntry ::=
	SEQUENCE {
		psmMiscDiameterRunningLevelName DisplayString,
		psmMiscDiameterRunningLevelVal  INTEGER
	}

psmMiscDiameterRunningLevelName OBJECT-TYPE
	SYNTAX      DisplayString
	MAX-ACCESS  not-accessible
	STATUS      current
	DESCRIPTION
	"Diameter running"
	::={ psmMiscDiameterRunningLevelEntry 1}

psmMiscDiameterRunningLevelVal OBJECT-TYPE
	SYNTAX     INTEGER {
		false(0),
		true(1)
	}
	MAX-ACCESS read-only
	STATUS     current
	DESCRIPTION
	"Diameter running"
	::={ psmMiscDiameterRunningLevelEntry 2 }

psmMiscSnooperDispatched OBJECT IDENTIFIER ::= { psmMisc 4 }

psmMiscSnooperDispatchedVal OBJECT-TYPE
	SYNTAX     Counter64
	MAX-ACCESS read-only
	STATUS     current
	DESCRIPTION "Snooper dispatched"

	::={ psmMiscSnooperDispatched 1 }

psmMiscSnooperDispatchedMom OBJECT-TYPE
	SYNTAX     CounterBasedGauge64
	MAX-ACCESS read-only
	STATUS     current
	DESCRIPTION "Snooper dispatched"

	::={ psmMiscSnooperDispatched 2 }

psmMiscSnooperDispatchedMax OBJECT-TYPE
	SYNTAX     CounterBasedGauge64
	MAX-ACCESS read-only
	STATUS     current
	DESCRIPTION "Snooper dispatched"

	::={ psmMiscSnooperDispatched 3 }

psmMiscSnooperDispatchedLevelTable OBJECT-TYPE
	SYNTAX     SEQUENCE OF PsmMiscSnooperDispatchedLevelEntry
	MAX-ACCESS not-accessible
	STATUS     current
	DESCRIPTION
	"Snooper dispatched"
	::={ psmMiscSnooperDispatched 4 }

psmMiscSnooperDispatchedLevelEntry OBJECT-TYPE
	SYNTAX      PsmMiscSnooperDispatchedLevelEntry
	MAX-ACCESS  not-accessible
	STATUS      current
	DESCRIPTION
	"Snooper dispatched"
	INDEX { psmMiscSnooperDispatchedLevelName }
	::={ psmMiscSnooperDispatchedLevelTable 1 }

PsmMiscSnooperDispatchedLevelEntry ::=
	SEQUENCE {
		psmMiscSnooperDispatchedLevelName DisplayString,
		psmMiscSnooperDispatchedLevelVal  Counter64,
		psmMiscSnooperDispatchedLevelMom  CounterBasedGauge64,
		psmMiscSnooperDispatchedLevelMax  CounterBasedGauge64
	}

psmMiscSnooperDispatchedLevelName OBJECT-TYPE
	SYNTAX      DisplayString
	MAX-ACCESS  not-accessible
	STATUS      current
	DESCRIPTION
	"Snooper dispatched"
	::={ psmMiscSnooperDispatchedLevelEntry 1}

psmMiscSnooperDispatchedLevelVal OBJECT-TYPE
	SYNTAX     Counter64
	MAX-ACCESS read-only
	STATUS     current
	DESCRIPTION
	"Snooper dispatched"
	::={ psmMiscSnooperDispatchedLevelEntry 2 }

psmMiscSnooperDispatchedLevelMom OBJECT-TYPE
	SYNTAX     CounterBasedGauge64
	MAX-ACCESS read-only
	STATUS     current
	DESCRIPTION
	"Snooper dispatched"
	::={ psmMiscSnooperDispatchedLevelEntry 3 }

psmMiscSnooperDispatchedLevelMax OBJECT-TYPE
	SYNTAX     CounterBasedGauge64
	MAX-ACCESS read-only
	STATUS     current
	DESCRIPTION
	"Snooper dispatched"
	::={ psmMiscSnooperDispatchedLevelEntry 4 }

psmMiscSnooperDropped OBJECT IDENTIFIER ::= { psmMisc 5 }

psmMiscSnooperDroppedVal OBJECT-TYPE
	SYNTAX     Counter64
	MAX-ACCESS read-only
	STATUS     current
	DESCRIPTION "Snooper dropped"

	::={ psmMiscSnooperDropped 1 }

psmMiscSnooperDroppedMom OBJECT-TYPE
	SYNTAX     CounterBasedGauge64
	MAX-ACCESS read-only
	STATUS     current
	DESCRIPTION "Snooper dropped"

	::={ psmMiscSnooperDropped 2 }

psmMiscSnooperDroppedMax OBJECT-TYPE
	SYNTAX     CounterBasedGauge64
	MAX-ACCESS read-only
	STATUS     current
	DESCRIPTION "Snooper dropped"

	::={ psmMiscSnooperDropped 3 }

psmMiscSnooperDroppedLevelTable OBJECT-TYPE
	SYNTAX     SEQUENCE OF PsmMiscSnooperDroppedLevelEntry
	MAX-ACCESS not-accessible
	STATUS     current
	DESCRIPTION
	"Snooper dropped"
	::={ psmMiscSnooperDropped 4 }

psmMiscSnooperDroppedLevelEntry OBJECT-TYPE
	SYNTAX      PsmMiscSnooperDroppedLevelEntry
	MAX-ACCESS  not-accessible
	STATUS      current
	DESCRIPTION
	"Snooper dropped"
	INDEX { psmMiscSnooperDroppedLevelName }
	::={ psmMiscSnooperDroppedLevelTable 1 }

PsmMiscSnooperDroppedLevelEntry ::=
	SEQUENCE {
		psmMiscSnooperDroppedLevelName DisplayString,
		psmMiscSnooperDroppedLevelVal  Counter64,
		psmMiscSnooperDroppedLevelMom  CounterBasedGauge64,
		psmMiscSnooperDroppedLevelMax  CounterBasedGauge64
	}

psmMiscSnooperDroppedLevelName OBJECT-TYPE
	SYNTAX      DisplayString
	MAX-ACCESS  not-accessible
	STATUS      current
	DESCRIPTION
	"Snooper dropped"
	::={ psmMiscSnooperDroppedLevelEntry 1}

psmMiscSnooperDroppedLevelVal OBJECT-TYPE
	SYNTAX     Counter64
	MAX-ACCESS read-only
	STATUS     current
	DESCRIPTION
	"Snooper dropped"
	::={ psmMiscSnooperDroppedLevelEntry 2 }

psmMiscSnooperDroppedLevelMom OBJECT-TYPE
	SYNTAX     CounterBasedGauge64
	MAX-ACCESS read-only
	STATUS     current
	DESCRIPTION
	"Snooper dropped"
	::={ psmMiscSnooperDroppedLevelEntry 3 }

psmMiscSnooperDroppedLevelMax OBJECT-TYPE
	SYNTAX     CounterBasedGauge64
	MAX-ACCESS read-only
	STATUS     current
	DESCRIPTION
	"Snooper dropped"
	::={ psmMiscSnooperDroppedLevelEntry 4 }

psmMiscSnooperDuplicates OBJECT IDENTIFIER ::= { psmMisc 6 }

psmMiscSnooperDuplicatesVal OBJECT-TYPE
	SYNTAX     Counter64
	MAX-ACCESS read-only
	STATUS     current
	DESCRIPTION "Snooper duplicates"

	::={ psmMiscSnooperDuplicates 1 }

psmMiscSnooperDuplicatesMom OBJECT-TYPE
	SYNTAX     CounterBasedGauge64
	MAX-ACCESS read-only
	STATUS     current
	DESCRIPTION "Snooper duplicates"

	::={ psmMiscSnooperDuplicates 2 }

psmMiscSnooperDuplicatesMax OBJECT-TYPE
	SYNTAX     CounterBasedGauge64
	MAX-ACCESS read-only
	STATUS     current
	DESCRIPTION "Snooper duplicates"

	::={ psmMiscSnooperDuplicates 3 }

psmMiscSnooperDuplicatesLevelTable OBJECT-TYPE
	SYNTAX     SEQUENCE OF PsmMiscSnooperDuplicatesLevelEntry
	MAX-ACCESS not-accessible
	STATUS     current
	DESCRIPTION
	"Snooper duplicates"
	::={ psmMiscSnooperDuplicates 4 }

psmMiscSnooperDuplicatesLevelEntry OBJECT-TYPE
	SYNTAX      PsmMiscSnooperDuplicatesLevelEntry
	MAX-ACCESS  not-accessible
	STATUS      current
	DESCRIPTION
	"Snooper duplicates"
	INDEX { psmMiscSnooperDuplicatesLevelName }
	::={ psmMiscSnooperDuplicatesLevelTable 1 }

PsmMiscSnooperDuplicatesLevelEntry ::=
	SEQUENCE {
		psmMiscSnooperDuplicatesLevelName DisplayString,
		psmMiscSnooperDuplicatesLevelVal  Counter64,
		psmMiscSnooperDuplicatesLevelMom  CounterBasedGauge64,
		psmMiscSnooperDuplicatesLevelMax  CounterBasedGauge64
	}

psmMiscSnooperDuplicatesLevelName OBJECT-TYPE
	SYNTAX      DisplayString
	MAX-ACCESS  not-accessible
	STATUS      current
	DESCRIPTION
	"Snooper duplicates"
	::={ psmMiscSnooperDuplicatesLevelEntry 1}

psmMiscSnooperDuplicatesLevelVal OBJECT-TYPE
	SYNTAX     Counter64
	MAX-ACCESS read-only
	STATUS     current
	DESCRIPTION
	"Snooper duplicates"
	::={ psmMiscSnooperDuplicatesLevelEntry 2 }

psmMiscSnooperDuplicatesLevelMom OBJECT-TYPE
	SYNTAX     CounterBasedGauge64
	MAX-ACCESS read-only
	STATUS     current
	DESCRIPTION
	"Snooper duplicates"
	::={ psmMiscSnooperDuplicatesLevelEntry 3 }

psmMiscSnooperDuplicatesLevelMax OBJECT-TYPE
	SYNTAX     CounterBasedGauge64
	MAX-ACCESS read-only
	STATUS     current
	DESCRIPTION
	"Snooper duplicates"
	::={ psmMiscSnooperDuplicatesLevelEntry 4 }

psmMiscSnooperLaunched OBJECT IDENTIFIER ::= { psmMisc 7 }

psmMiscSnooperLaunchedVal OBJECT-TYPE
	SYNTAX     CounterBasedGauge64
	MAX-ACCESS read-only
	STATUS     current
	DESCRIPTION "Snooper launched"

	::={ psmMiscSnooperLaunched 1 }

psmMiscSnooperLaunchedMax OBJECT-TYPE
	SYNTAX     CounterBasedGauge64
	MAX-ACCESS read-only
	STATUS     current
	DESCRIPTION "Snooper launched"

	::={ psmMiscSnooperLaunched 3 }

psmMiscSnooperLaunchedLevelTable OBJECT-TYPE
	SYNTAX     SEQUENCE OF PsmMiscSnooperLaunchedLevelEntry
	MAX-ACCESS not-accessible
	STATUS     current
	DESCRIPTION
	"Snooper launched"
	::={ psmMiscSnooperLaunched 4 }

psmMiscSnooperLaunchedLevelEntry OBJECT-TYPE
	SYNTAX      PsmMiscSnooperLaunchedLevelEntry
	MAX-ACCESS  not-accessible
	STATUS      current
	DESCRIPTION
	"Snooper launched"
	INDEX { psmMiscSnooperLaunchedLevelName }
	::={ psmMiscSnooperLaunchedLevelTable 1 }

PsmMiscSnooperLaunchedLevelEntry ::=
	SEQUENCE {
		psmMiscSnooperLaunchedLevelName DisplayString,
		psmMiscSnooperLaunchedLevelVal  CounterBasedGauge64,
		psmMiscSnooperLaunchedLevelMax  CounterBasedGauge64
	}

psmMiscSnooperLaunchedLevelName OBJECT-TYPE
	SYNTAX      DisplayString
	MAX-ACCESS  not-accessible
	STATUS      current
	DESCRIPTION
	"Snooper launched"
	::={ psmMiscSnooperLaunchedLevelEntry 1}

psmMiscSnooperLaunchedLevelVal OBJECT-TYPE
	SYNTAX     CounterBasedGauge64
	MAX-ACCESS read-only
	STATUS     current
	DESCRIPTION
	"Snooper launched"
	::={ psmMiscSnooperLaunchedLevelEntry 2 }

psmMiscSnooperLaunchedLevelMax OBJECT-TYPE
	SYNTAX     CounterBasedGauge64
	MAX-ACCESS read-only
	STATUS     current
	DESCRIPTION
	"Snooper launched"
	::={ psmMiscSnooperLaunchedLevelEntry 4 }

psmMiscSnooperRunning OBJECT IDENTIFIER ::= { psmMisc 8 }

psmMiscSnooperRunningVal OBJECT-TYPE
	SYNTAX     INTEGER {
		false(0),
		true(1)
	}
	MAX-ACCESS read-only
	STATUS     current
	DESCRIPTION "Snooper running"

	::={ psmMiscSnooperRunning 1 }

psmMiscSnooperRunningLevelTable OBJECT-TYPE
	SYNTAX     SEQUENCE OF PsmMiscSnooperRunningLevelEntry
	MAX-ACCESS not-accessible
	STATUS     current
	DESCRIPTION
	"Snooper running"
	::={ psmMiscSnooperRunning 4 }

psmMiscSnooperRunningLevelEntry OBJECT-TYPE
	SYNTAX      PsmMiscSnooperRunningLevelEntry
	MAX-ACCESS  not-accessible
	STATUS      current
	DESCRIPTION
	"Snooper running"
	INDEX { psmMiscSnooperRunningLevelName }
	::={ psmMiscSnooperRunningLevelTable 1 }

PsmMiscSnooperRunningLevelEntry ::=
	SEQUENCE {
		psmMiscSnooperRunningLevelName DisplayString,
		psmMiscSnooperRunningLevelVal  INTEGER
	}

psmMiscSnooperRunningLevelName OBJECT-TYPE
	SYNTAX      DisplayString
	MAX-ACCESS  not-accessible
	STATUS      current
	DESCRIPTION
	"Snooper running"
	::={ psmMiscSnooperRunningLevelEntry 1}

psmMiscSnooperRunningLevelVal OBJECT-TYPE
	SYNTAX     INTEGER {
		false(0),
		true(1)
	}
	MAX-ACCESS read-only
	STATUS     current
	DESCRIPTION
	"Snooper running"
	::={ psmMiscSnooperRunningLevelEntry 2 }

END
