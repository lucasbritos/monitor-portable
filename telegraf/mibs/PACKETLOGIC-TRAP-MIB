PACKETLOGIC-TRAP-MIB DEFINITIONS ::= BEGIN

IMPORTS
	NOTIFICATION-TYPE,
	MODULE-IDENTITY, OBJECT-TYPE, Integer32, Counter64,
	Unsigned32, TimeTicks FROM SNMPv2-SMI
	packetlogic2 FROM PACKETLOGIC-MIB
	DisplayString, DateAndTime FROM SNMPv2-TC
	CounterBasedGauge64 FROM HCNUM-TC;

pl2Trap MODULE-IDENTITY
	LAST-UPDATED "201711101327Z"
	ORGANIZATION "Procera Networks, Inc."
	CONTACT-INFO "support@proceranetworks.com"
	DESCRIPTION "MIB for PacketLogic2 traps"
	REVISION "201711101327Z"
	DESCRIPTION " Latest version at the revision date for version GET VERSION HERE"

	::={packetlogic2 8}
pl2Traps	OBJECT IDENTIFIER ::={pl2Trap 0}

pl2TrapVals	OBJECT IDENTIFIER ::={pl2Trap 1}












pl2ChannelTraps	OBJECT IDENTIFIER ::={pl2Trap 2}


pl2ChannelTrapVals	OBJECT IDENTIFIER ::={pl2Trap 3}






pl2StorageTrapVals	OBJECT IDENTIFIER ::={pl2Trap 4}






pl2ContentLogicTraps	OBJECT IDENTIFIER ::={pl2Trap 5}

pl2ContentLogicHourlyUpdateTraps	OBJECT IDENTIFIER ::={pl2ContentLogicTraps 1}

pl2ContentLogicCategoriesLoadingTraps	OBJECT IDENTIFIER ::={pl2ContentLogicTraps 2}

pl2ContentLogicDatabaseUpdateTraps	OBJECT IDENTIFIER ::={pl2ContentLogicTraps 3}

pl2ContentLogicDatabaseLoadingTraps	OBJECT IDENTIFIER ::={pl2ContentLogicTraps 4}

pl2ContentLogicTrapVals	OBJECT IDENTIFIER ::={pl2Trap 6}
















pl2TrapMessage	OBJECT-TYPE
	SYNTAX	 DisplayString
	MAX-ACCESS read-only
	STATUS current
	DESCRIPTION "Message describing trap."

	::={pl2TrapVals 1}

pl2TrapOid	OBJECT-TYPE
	SYNTAX	 OBJECT IDENTIFIER
	MAX-ACCESS read-only
	STATUS current
	DESCRIPTION "OID Causing trap."

	::={pl2TrapVals 2}

pl2TrapValue	OBJECT-TYPE
	SYNTAX	 Unsigned32
	MAX-ACCESS read-only
	STATUS current
	DESCRIPTION "Current value of item causing trap."

	::={pl2TrapVals 3}

pl2TrapThreshold	OBJECT-TYPE
	SYNTAX	 Unsigned32
	MAX-ACCESS read-only
	STATUS current
	DESCRIPTION "Threshold of item causing trap."

	::={pl2TrapVals 4}

pl2TrapValue64	OBJECT-TYPE
	SYNTAX	 Counter64
	MAX-ACCESS read-only
	STATUS current
	DESCRIPTION "Current value of item causing trap."

	::={pl2TrapVals 5}

pl2TrapThreshold64	OBJECT-TYPE
	SYNTAX	 Counter64
	MAX-ACCESS read-only
	STATUS current
	DESCRIPTION "Threshold of item causing trap."

	::={pl2TrapVals 6}

channelIndex	OBJECT-TYPE
	SYNTAX	 Unsigned32
	MAX-ACCESS read-only
	STATUS current
	DESCRIPTION "Index of the channel."

	::={pl2ChannelTrapVals 1}

channelDescr	OBJECT-TYPE
	SYNTAX	 DisplayString
	MAX-ACCESS read-only
	STATUS current
	DESCRIPTION "A description of the channel."

	::={pl2ChannelTrapVals 2}

channelPort	OBJECT-TYPE
	SYNTAX INTEGER { external(0), internal(1) }
	MAX-ACCESS read-only
	STATUS current
	DESCRIPTION "The port of the channel."

	::={pl2ChannelTrapVals 3}

prevState	OBJECT-TYPE
	SYNTAX INTEGER { auto(0), hd-10(1), fd-10(2), hd-100(3), fd-100(4), fd-1000(5), fd-10000(6), fd-40000(7), fd-100000(8) }
	MAX-ACCESS read-only
	STATUS current
	DESCRIPTION "This is the state the channel was in before it changed."

	::={pl2ChannelTrapVals 4}

newState	OBJECT-TYPE
	SYNTAX INTEGER { auto(0), hd-10(1), fd-10(2), hd-100(3), fd-100(4), fd-1000(5), fd-10000(6), fd-40000(7), fd-100000(8) }
	MAX-ACCESS read-only
	STATUS current
	DESCRIPTION "This is the new state of the channel."

	::={pl2ChannelTrapVals 5}

pl2ContentLogicDatabase	OBJECT-TYPE
	SYNTAX	 DisplayString
	MAX-ACCESS read-only
	STATUS current
	DESCRIPTION "Name of the database."

	::={pl2ContentLogicTrapVals 1}

pl2ContentLogicReason	OBJECT-TYPE
	SYNTAX	 DisplayString
	MAX-ACCESS read-only
	STATUS current
	DESCRIPTION "Reason for the failed event."

	::={pl2ContentLogicTrapVals 2}


pl2TrapGenericMsg NOTIFICATION-TYPE
	OBJECTS {pl2TrapMessage}
	STATUS current
	DESCRIPTION "Used for generic or undefined alerts. A message briefly explains the alert."
	::= {  pl2Traps 1 }

pl2TrapGeneric NOTIFICATION-TYPE
	STATUS current
	DESCRIPTION "Used for generic or undefined alerts without message. Should be avoided."
	::= {  pl2Traps 2 }

pl2TrapSystemStatsAlert NOTIFICATION-TYPE
	OBJECTS {pl2TrapThreshold, pl2TrapMessage, pl2TrapValue, pl2TrapOid}
	STATUS current
	DESCRIPTION "An Alert Threshold defined in SystemStats (System Diagnostics) was reached. This trap is used for items with 32 bit values."
	::= {  pl2Traps 3 }

pl2TrapSystemStatsAlert64 NOTIFICATION-TYPE
	OBJECTS {pl2TrapThreshold64, pl2TrapMessage, pl2TrapValue64, pl2TrapOid}
	STATUS current
	DESCRIPTION "An Alert Threshold defined in SystemStats (System Diagnostics) was reached. This trap is used for items with 64 bit values."
	::= {  pl2Traps 4 }

pl2TrapSystemStatsAlertClear NOTIFICATION-TYPE
	OBJECTS {pl2TrapOid}
	STATUS current
	DESCRIPTION "An Alert Threshold defined in SystemStats (System Diagnostics) is now clear."
	::= {  pl2Traps 5 }

pl2ChannelStateChanged NOTIFICATION-TYPE
	OBJECTS {channelIndex, channelDescr, channelPort, newState, prevState}
	STATUS current
	DESCRIPTION "Channel state changed"
	::= {  pl2ChannelTraps 1 }

pl2StorageGenericTrap NOTIFICATION-TYPE
	OBJECTS {pl2TrapMessage}
	STATUS current
	DESCRIPTION "Generic or undefined alerts from the storage devices."
	::= {  pl2StorageTrapVals 1 }

pl2StorageBattery NOTIFICATION-TYPE
	OBJECTS {pl2TrapMessage}
	STATUS current
	DESCRIPTION "Alerts regarding batteries in storage devices."
	::= {  pl2StorageTrapVals 2 }

pl2StoragePowerSupply NOTIFICATION-TYPE
	OBJECTS {pl2TrapMessage}
	STATUS current
	DESCRIPTION "Alerts for power supplies in storage devices."
	::= {  pl2StorageTrapVals 3 }

pl2StoragePhysicalDisk NOTIFICATION-TYPE
	OBJECTS {pl2TrapMessage}
	STATUS current
	DESCRIPTION "Alerts for physical disks in storage devices."
	::= {  pl2StorageTrapVals 4 }

pl2StorageVirtualDisk NOTIFICATION-TYPE
	OBJECTS {pl2TrapMessage}
	STATUS current
	DESCRIPTION "Alerts for virtual disks in storage devices."
	::= {  pl2StorageTrapVals 5 }

pl2ContentLogicHourlyUpdateStarted NOTIFICATION-TYPE
	STATUS current
	DESCRIPTION "A trap for notifying that ContentLogic has started an hourly update."
	::= {  pl2ContentLogicHourlyUpdateTraps 1 }

pl2ContentLogicHourlyUpdateCompleted NOTIFICATION-TYPE
	STATUS current
	DESCRIPTION "A trap for notifying that ContentLogic has completed an hourly update."
	::= {  pl2ContentLogicHourlyUpdateTraps 2 }

pl2ContentLogicHourlyUpdateFailed NOTIFICATION-TYPE
	OBJECTS {pl2ContentLogicReason}
	STATUS current
	DESCRIPTION "A trap for notifying that ContentLogic has failed an hourly update."
	::= {  pl2ContentLogicHourlyUpdateTraps 3 }

pl2ContentLogicCategoriesLoadingStarted NOTIFICATION-TYPE
	OBJECTS {pl2ContentLogicDatabase}
	STATUS current
	DESCRIPTION "A trap for notifying that ContentLogic has started to load categories."
	::= {  pl2ContentLogicCategoriesLoadingTraps 1 }

pl2ContentLogicCategoriesLoadingCompleted NOTIFICATION-TYPE
	OBJECTS {pl2ContentLogicDatabase}
	STATUS current
	DESCRIPTION "A trap for notifying that ContentLogic has completed loading categories."
	::= {  pl2ContentLogicCategoriesLoadingTraps 2 }

pl2ContentLogicCategoriesLoadingFailed NOTIFICATION-TYPE
	OBJECTS {pl2ContentLogicDatabase, pl2ContentLogicReason}
	STATUS current
	DESCRIPTION "A trap for notifying that ContentLogic has failed to load categories."
	::= {  pl2ContentLogicCategoriesLoadingTraps 3 }

pl2ContentLogicDatabaseUpdateStarted NOTIFICATION-TYPE
	OBJECTS {pl2ContentLogicDatabase}
	STATUS current
	DESCRIPTION "A trap for notifying that ContentLogic has started to update a database."
	::= {  pl2ContentLogicDatabaseUpdateTraps 1 }

pl2ContentLogicDatabaseUpdateCompleted NOTIFICATION-TYPE
	OBJECTS {pl2ContentLogicDatabase}
	STATUS current
	DESCRIPTION "A trap for notifying that ContentLogic has completed updating a database."
	::= {  pl2ContentLogicDatabaseUpdateTraps 2 }

pl2ContentLogicDatabaseUpdateFailed NOTIFICATION-TYPE
	OBJECTS {pl2ContentLogicDatabase, pl2ContentLogicReason}
	STATUS current
	DESCRIPTION "A trap for notifying that ContentLogic has failed to update a database."
	::= {  pl2ContentLogicDatabaseUpdateTraps 3 }

pl2ContentLogicDatabaseLoadingStarted NOTIFICATION-TYPE
	OBJECTS {pl2ContentLogicDatabase}
	STATUS current
	DESCRIPTION "A trap for notifying that ContentLogic has started to load a database."
	::= {  pl2ContentLogicDatabaseLoadingTraps 1 }

pl2ContentLogicDatabaseLoadingCompleted NOTIFICATION-TYPE
	OBJECTS {pl2ContentLogicDatabase}
	STATUS current
	DESCRIPTION "A trap for notifying that ContentLogic has completed loading a database."
	::= {  pl2ContentLogicDatabaseLoadingTraps 2 }

pl2ContentLogicDatabaseLoadingFailed NOTIFICATION-TYPE
	OBJECTS {pl2ContentLogicDatabase, pl2ContentLogicReason}
	STATUS current
	DESCRIPTION "A trap for notifying that ContentLogic has failed to load a database."
	::= {  pl2ContentLogicDatabaseLoadingTraps 3 }


END
